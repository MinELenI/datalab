FME workspace INSPIRE_NWB_v2.fmw

Parameters:
- SourceDataset_POSTGIS = pdok   # Source PostGIS Dataset

Readers:
- POSTGIS_1: POSTGIS from $(SourceDataset_POSTGIS)

Writers:
- POSTGIS_2: POSTGIS to pdok

nwbwegen.wegvakken_imp (reader POSTGIS_1)
    attributes: gid serial,PRIKEY, wvk_id float8, wvk_begdat date, jte_id_beg float8, jte_id_end float8, wegbehsrt varchar(1), wegnummer varchar(5), wegdeelltr varchar(1), hecto_lttr varchar(1), baansubsrt varchar(3), rpe_code varchar(2), admrichtng varchar(1), rijrichtng varchar(1), stt_naam varchar(29), wpsnaamnen varchar(24), gme_id int2, gme_naam varchar(24), hnrstrlnks varchar(1), hnrstrrhts varchar(1), e_hnr_lnks int4, e_hnr_rhts int4, l_hnr_lnks int4, l_hnr_rhts int4, begafstand int4, endafstand int4, beginkm float8, eindkm float8, pos_tv_wol varchar(1), geom_valid bool
    -> Reprojector
Reprojector
    DEST = EPSG:4258
    SOURCE = EPSG:28992
    RASTER_CELL_SIZE = Preserve Cells
    INTERPOLATION_TYPE_NAME = Nearest Neighbor
    STROKE_ARCS = Yes
    REPROJECTED -> DateFormatter
DateFormatter
    FMT = XML DateTime (%Y-%m-%dT%H:%M:%S)
    DATE_ATTR = wvk_begdat
    -> CoordinateSwapper
CoordinateSwapper
    SWAP_TYPE = X <-> Y
    -> CoordinateConcatenator
CoordinateConcatenator
    COORD_ATTR = _coordinates
    COORD_DELIM = ,
    COORDINATES_TO_INCLUDE_DIS = X Y
    ELEMENT_DELIM = ,
    -> CoordinateSwapper_2
CoordinateSwapper_2
    SWAP_TYPE = X <-> Y
    -> StringReplacer
StringReplacer
    FIND_TEXT = ^2,[0123456789]*,
    SRC_ATTRS = _coordinates
    REGEXP = yes
    CASE = no
    -> XMLTemplater
XMLTemplater
    OUTPUT_XML_HEADER = Yes
    VISIBLE_QUERY_VALIDATE = No
    ROOT_QUERY_EXPR:
      <?xml version="1.0" encoding="UTF-8"?>
      <base:SpatialDataSet xmlns:gml="http://www.opengis.net/gml/3.2"
                  xmlns:gn="urn:x-inspire:specification:gmlas:GeographicalNames:3.0"
                  xmlns:net="urn:x-inspire:specification:gmlas:Network:3.2"
                  xmlns:tn="urn:x-inspire:specification:gmlas:CommonTransportElements:3.0"
                  xmlns:tn-ro="urn:x-inspire:specification:gmlas:RoadTransportNetwork:3.0"
                  xmlns:gco="http://www.isotc211.org/2005/gco"
                  xmlns:xlink="http://www.w3.org/1999/xlink"
                  xmlns:base="urn:x-inspire:specification:gmlas:BaseTypes:3.2"
                  xmlns:gmd="http://www.isotc211.org/2005/gmd" xmlns:gsr="http://www.isotc211.org/2005/gsr"
                  xmlns:gts="http://www.isotc211.org/2005/gts" xmlns:gss="http://www.isotc211.org/2005/gss"
                  xsi:schemaLocation="urn:x-inspire:specification:gmlas:BaseTypes:3.2 http://inspire.ec.europa.eu/schemas/base/3.2/BaseTypes.xsd
                                      urn:x-inspire:specification:gmlas:Network:3.2 http://inspire.ec.europa.eu/schemas/net/3.2/Network.xsd
                                      urn:x-inspire:specification:gmlas:CommonTransportElements:3.0 http://inspire.ec.europa.eu/schemas/tn/3.0/CommonTransportElements.xsd
                                      urn:x-inspire:specification:gmlas:RoadTransportNetwork:3.0 http://inspire.ec.europa.eu/schemas/tn-ro/3.0/RoadTransportNetwork.xsd
                                      urn:x-inspire:specification:gmlas:GeographicalNames:3.0 http://inspire.ec.europa.eu/schemas/gn/3.0/GeographicalNames.xsd"
                  gml:id="NL.RWS.NWB.TN_RO">
          <base:identifier>
              <base:Identifier>
                  <base:localId>0</base:localId>
                  <base:namespace>NL.RWS.NWB.TN_RO</base:namespace>
              </base:Identifier>
          </base:identifier>
          <base:metadata xsi:nil="true"/>
      <base:member>
      <tn-ro:Road gml:id="NL.RWS.NWB.TN_RO.{fme:get-attribute("gid")}">
        <gml:identifier codeSpace="http://inspire.jrc.ec.europa.eu/">urn:x-inspire:object:id:NL.RWS.NWB.TN_RO.{fme:get-attribute('gid')}</gml:identifier>
        <net:beginLifespanVersion>{fme:get-attribute("wvk_begdat")}</net:beginLifespanVersion>
        <net:inspireId>
          <base:Identifier>
            <base:localId>{fme:get-attribute("gid")}</base:localId>
            <base:namespace>NL.RWS.NWB.TN_RO</base:namespace>
            <base:versionId>0</base:versionId>
          </base:Identifier>
        </net:inspireId>
        <net:endLifespanVersion nilReason="other:unpopulated" xsi:nil="true"></net:endLifespanVersion>
        <net:inNetwork owns="false" nilReason="" gml:remoteSchema="" xlink:type="simple" xlink:href="" xlink:role="none" xlink:arcrole="none" xlink:title="" xlink:show="none" xlink:actuate="none"/>
        <net:link nilReason="" gml:remoteSchema="" xlink:type="simple" xlink:href="" xlink:role="none" xlink:arcrole="none" xlink:title="" xlink:show="none" xlink:actuate="none" owns="false"/>
        <tn:geographicalName>
          <gn:GeographicalName>
            <gn:language>NL</gn:language>
            <gn:nativeness>endonym</gn:nativeness>
            <gn:nameStatus nilReason="other:unpopulated" xsi:nil="true"></gn:nameStatus>
            <gn:sourceOfName>RijksWaterstaat</gn:sourceOfName>
            <gn:pronunciation nilReason="other:unpopulated" xsi:nil="true"></gn:pronunciation>
            <gn:spelling>
              <gn:SpellingOfName>
                <gn:text>{fme:get-attribute("stt_naam")}</gn:text>
                <gn:script>Latn</gn:script>
                <gn:transliterationScheme nilReason="other:unpopulated" xsi:nil="true"></gn:transliterationScheme>
              </gn:SpellingOfName>
            </gn:spelling>
            <gn:grammaticalGender nilReason="other:unpopulated" xsi:nil="true"></gn:grammaticalGender>
            <gn:grammaticalNumber nilReason="other:unpopulated" xsi:nil="true"></gn:grammaticalNumber>
          </gn:GeographicalName>
        </tn:geographicalName>
        <tn:validFrom>{fme:get-attribute("wvk_begdat")}</tn:validFrom>
        <tn:validTo nilReason="other:unpopulated" xsi:nil="true"></tn:validTo>
        <tn:post owns="false" nilReason="other:unpopulated" xsi:nil="true"/>
        <tn-ro:localRoadCode>{fme:get-attribute("wegnummer")}</tn-ro:localRoadCode>
        <tn-ro:nationalRoadCode>{fme:get-attribute("wegnummer")}</tn-ro:nationalRoadCode>
      </tn-ro:Road>
      </base:member>
      <base:member>
      <tn-ro:RoadLink gml:id="NL.RWS.NWB.TN_RL.{fme:get-attribute("gid")}">
        <gml:identifier codeSpace="http://inspire.jrc.ec.europa.eu/">urn:x-inspire:object:id:NL.RWS.NWB.TN_RL.{fme:get-attribute('gid')}</gml:identifier>
        <net:beginLifespanVersion>{fme:get-attribute("wvk_begdat")}</net:beginLifespanVersion>
        <net:inspireId>
          <base:Identifier>
            <base:localId>{fme:get-attribute("gid")}</base:localId>
            <base:namespace>NL.RWS.NWB.TN_RL</base:namespace>
            <base:versionId>0</base:versionId>
          </base:Identifier>
        </net:inspireId>
        <net:endLifespanVersion nilReason="other:unpopulated" xsi:nil="true"></net:endLifespanVersion>
        <net:inNetwork owns="false" nilReason="" gml:remoteSchema="" xlink:type="simple" xlink:href="" xlink:role="none" xlink:arcrole="none" xlink:title="" xlink:show="none" xlink:actuate="none"/>
        <net:centrelineGeometry nilReason="" gml:remoteSchema="" xlink:type="simple" xlink:href="" xlink:role="none" xlink:arcrole="none" xlink:title="" xlink:show="none" xlink:actuate="none" owns="false">
          <gml:LineString srsName="urn:ogc:def:crs:EPSG::4258" srsDimension="2" gml:id="NL.KAD.BAG.Address.{fme:get-attribute('identificatie')}_L">
            <gml:coordinates>"{fme:get-attribute('_coordinates')}"</gml:coordinates>
          </gml:LineString>
        </net:centrelineGeometry>
        <net:fictitious>false</net:fictitious>
        <net:endNode owns="false" nilReason="" gml:remoteSchema="" xlink:type="simple" xlink:href="" xlink:role="none" xlink:arcrole="none" xlink:title="" xlink:show="none" xlink:actuate="none"/>
        <net:startNode owns="false" nilReason="" gml:remoteSchema="" xlink:type="simple" xlink:href="" xlink:role="none" xlink:arcrole="none" xlink:title="" xlink:show="none" xlink:actuate="none"/>
        <tn:geographicalName>
          <gn:GeographicalName>
            <gn:language>NL</gn:language>
            <gn:nativeness>endonym</gn:nativeness>
            <gn:nameStatus nilReason="other:unpopulated" xsi:nil="true"></gn:nameStatus>
            <gn:sourceOfName>RijksWaterstaat</gn:sourceOfName>
            <gn:pronunciation nilReason="other:unpopulated" xsi:nil="true"></gn:pronunciation>
            <gn:spelling>
              <gn:SpellingOfName>
                <gn:text>{fme:get-attribute("stt_naam")}</gn:text>
                <gn:script>Latn</gn:script>
                <gn:transliterationScheme nilReason="other:unpopulated" xsi:nil="true"></gn:transliterationScheme>
              </gn:SpellingOfName>
            </gn:spelling>
            <gn:grammaticalGender nilReason="other:unpopulated" xsi:nil="true"></gn:grammaticalGender>
            <gn:grammaticalNumber nilReason="other:unpopulated" xsi:nil="true"></gn:grammaticalNumber>
          </gn:GeographicalName>
        </tn:geographicalName>
        <tn:validFrom>{fme:get-attribute("wvk_begdat")}</tn:validFrom>
        <tn:validTo nilReason="other:unpopulated" xsi:nil="true"></tn:validTo>
      </tn-ro:RoadLink>
      </base:member>
      </base:SpatialDataSet>
    RESULT_ATTRIBUTE = _result
    -> AttributeCreator
AttributeCreator
    ATTR_LIST = ft_type,61,gml_id,fme_basicstring:17%11:NL.RWS.NWB.TN_RO.@Value(gid),binary_object,@Value(_result)
    -> AttributeExpressionRemover
AttributeExpressionRemover
    ATTR_EXP = post*
    -> BinaryEncoder
BinaryEncoder
    DEST_ATTR = binary_object
    ENCODING_TYPE = HEX
    ATTR_TO_ENCODE = binary_object
    -> inspire_tn_blob.gml_objects (writer POSTGIS_2)
inspire_tn_blob.gml_objects (writer POSTGIS_2)
    attributes: id serial,PRIKEY, gml_id text,none, ft_type int2, binary_object bytea
