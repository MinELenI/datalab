FME workspace postgres2XML.fmw

Parameters:
- XML_DIR = H:\Projects\PDOK\NWB_WEGEN\Scripts2PG\XML_uit   # Fanout Directory
- LOG_FILE =   # Log File
- FT_TYPE = 61   # Type object
- MAX_FEATURES =   # Max Features to Read

Readers:
- POSTGRES_1: POSTGRES from pdok

Writers:
- TEXTLINE_1: TEXTLINE to H:\Projects\PDOK\Scripts2PG\XML_uit\test_5.xml

inspire_tn.gml_objects (reader POSTGRES_1)
    attributes: id serial,PRIKEY, gml_id text,PRIKEY, ft_type int2, binary_object bytea, gml_bounded_by char(80),GIST
    -> BinaryDecoder
BinaryDecoder
    ATTR_ENCODING = utf-8
    ATTR_TO_DECODE = binary_object
    ENCODING_TYPE = HEX
    DEST_ATTR = _decoded
    -> AttributeCreator
AttributeCreator
    ATTR_LIST:
      text_line_data,<base:SpatialDataSet xmlns:gml="http://www.opengis.net/gml/3.2"
                  xmlns:gn="urn:x-inspire:specification:gmlas:GeographicalNames:3.0"
                  xmlns:net="urn:x-inspire:specification:gmlas:Network:3.2"
                  xmlns:tn="urn:x-inspire:specification:gmlas:CommonTransportElements:3.0"
                  xmlns:tn-ro="urn:x-inspire:specification:gmlas:RoadTransportNetwork:3.0"
                  xmlns:gco="http://www.isotc211.org/2005/gco"
                  xmlns:xsi="http://www.w3.org/2001/XMLSchema-instance"
                  xmlns:xlink="http://www.w3.org/1999/xlink"
                  xmlns:base="urn:x-inspire:specification:gmlas:BaseTypes:3.2"
                  xmlns:gmd="http://www.isotc211.org/2005/gmd" xmlns:gsr="http://www.isotc211.org/2005/gsr"
                  xmlns:gts="http://www.isotc211.org/2005/gts" xmlns:gss="http://www.isotc211.org/2005/gss"
                  xsi:schemaLocation="urn:x-inspire:specification:gmlas:BaseTypes:3.2 http://inspire.ec.europa.eu/schemas/base/3.2/BaseTypes.xsd
                                      urn:x-inspire:specification:gmlas:Network:3.2 http://inspire.ec.europa.eu/schemas/net/3.2/Network.xsd
                                      urn:x-inspire:specification:gmlas:CommonTransportElements:3.0 http://inspire.ec.europa.eu/schemas/tn/3.0/CommonTransportElements.xsd
                                      urn:x-inspire:specification:gmlas:RoadTransportNetwork:3.0 http://inspire.ec.europa.eu/schemas/tn-ro/3.0/RoadTransportNetwork.xsd
                                      urn:x-inspire:specification:gmlas:GeographicalNames:3.0 http://inspire.ec.europa.eu/schemas/gn/3.0/GeographicalNames.xsd"
                   gml:id="TransportNetwork.1">
        <base:identifier>
          <base:Identifier>
            <base:localId>0</base:localId>
            <base:namespace>NL.RWS.NWB</base:namespace>
            <base:versionId xsi:nil="true" nilReason="other:unpopulated"/>
          </base:Identifier>
        </base:identifier>
        <base:metadata xsi:nil="true"/>
       <base:member>
      @Value(_decoded)
       </base:member>
      </base:SpatialDataSet>
    -> text_line (writer TEXTLINE_1)
text_line (writer TEXTLINE_1)
    attributes: text_line_data buffer
