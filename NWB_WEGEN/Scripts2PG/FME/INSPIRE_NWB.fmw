FME workspace INSPIRE_NWB.fmw

Parameters:
- LOG_FILE =   # Log File
- MAX_FEATURES = 1000   # Max Features to Read
- SourceDataset_SHAPE = ""D:\Projects\PDOK\NWB_WEGEN\Scripts2PG\Data\rijstroken.shp" "D:\Projects\PDOK\NWB_WEGEN\Scripts2PG\Data\max_snelheden.shp""   # Source Esri Shape File(s)

Readers:
- POSTGIS_1: POSTGIS from pdok
- SHAPE_1: SHAPE from $(SourceDataset_SHAPE)

Writers:
- POSTGIS_2: POSTGIS to pdok

nwbwegen.wegvakken_imp (reader POSTGIS_1)
    attributes: gid serial,PRIKEY, wvk_id float8, wvk_begdat date, jte_id_beg float8, jte_id_end float8, wegbehsrt varchar(1), wegnummer varchar(5), wegdeelltr varchar(1), hecto_lttr varchar(1), baansubsrt varchar(3), rpe_code varchar(2), admrichtng varchar(1), rijrichtng varchar(1), stt_naam varchar(29), wpsnaamnen varchar(24), gme_id int2, gme_naam varchar(24), hnrstrlnks varchar(1), hnrstrrhts varchar(1), e_hnr_lnks int4, e_hnr_rhts int4, l_hnr_lnks int4, l_hnr_rhts int4, begafstand int4, endafstand int4, beginkm float8, eindkm float8, pos_tv_wol varchar(1), geom_valid bool
    -> FeatureMerger_2 [input 1]
rijstroken (reader SHAPE_1)
    attributes: OMSCHR char(40), VOLGNRSTRK char(3), KANTCODE char(1), WVK_ID number(10,0), WVK_BEGDAT date, BEGAFSTAND number(8,0), ENDAFSTAND number(8,0), FK_VELD1 char(20), FK_VELD4 char(13), IZI_SIDE char(1), SHAPE_LEN number(19,11)
    -> AttributeCopier
AttributeCopier
    ATTR_LIST = RIJSTROKEN,OMSCHR
    -> GeometryRemover
GeometryRemover
    -> AttributeKeeper
AttributeKeeper
    KEEP_ATTRS = RIJSTROKEN,WVK_ID
    -> FeatureMerger [input 1]
max_snelheden (reader SHAPE_1)
    attributes: OMSCHR number(8,0), KANTCODE char(1), WVK_ID number(10,0), WVK_BEGDAT date, BEGAFSTAND number(8,0), ENDAFSTAND number(8,0), FK_VELD1 char(20), FK_VELD4 char(13), IZI_SIDE char(1), SHAPE_LEN number(19,11)
    -> AttributeCopier_2
AttributeCopier_2
    ATTR_LIST = MAX_SNELHEID,OMSCHR
    -> GeometryRemover_2
GeometryRemover_2
    -> AttributeKeeper_2
AttributeKeeper_2
    KEEP_ATTRS = MAX_SNELHEID,WVK_ID
    -> FeatureMerger [input 2]
FeatureMerger
    BUILD_INCOMPLETE = Yes
    PROCESS_DUPS = No
    MERGE_TYPE = Attributes Only
    REFERATTR = WVK_ID
    REFEEATTR = WVK_ID
    COMPLETE -> AttributeRenamer
    INCOMPLETE -> AttributeRenamer
AttributeRenamer
    ATTR_LIST = WVK_ID,wvk_id,""
    -> FeatureMerger_2 [input 2]
FeatureMerger_2
    BUILD_INCOMPLETE = Yes
    PROCESS_DUPS = No
    MERGE_TYPE = Attributes Only
    REFERATTR = wvk_id
    REFEEATTR = wvk_id
    COMPLETE -> Reprojector
    INCOMPLETE -> Reprojector
Reprojector
    DEST = EPSG:4258
    RASTER_CELL_SIZE = Preserve Cells
    STROKE_ARCS = Yes
    SOURCE = EPSG:28992
    INTERPOLATION_TYPE_NAME = Nearest Neighbor
    REPROJECTED -> DateFormatter
DateFormatter
    DATE_ATTR = wvk_begdat
    FMT = %Y-%m-%dT00:00:00
    -> CoordinateSwapper
CoordinateSwapper
    SWAP_TYPE = X <-> Y
    -> 3DForcer
3DForcer
    ZVALATTR = 0
    -> CoordinateConcatenator
CoordinateConcatenator
    COORD_ATTR = _coordinates
    COORD_DELIM = " "
    COORDINATES_TO_INCLUDE_DIS = X Y Z
    ELEMENT_DELIM = ,
    -> CoordinateSwapper_2
CoordinateSwapper_2
    SWAP_TYPE = X <-> Y
    -> StringReplacer
StringReplacer
    SRC_ATTRS = _coordinates
    REGEXP = yes
    CASE = no
    FIND_TEXT = "^2,[0123456789]*,0 "
    -> XMLTemplater_Road
    -> XMLTemplater_Roadlink
    -> Tester_RIJSTROKEN
    -> Tester_MAX_SNELHEID
XMLTemplater_Road
    RESULT_ATTRIBUTE = _result
    ROOT_QUERY_EXPR:
      <tn-ro:Road xmlns:gml="http://www.opengis.net/gml/3.2" xmlns:gn="urn:x-inspire:specification:gmlas:GeographicalNames:3.0" xmlns:net="urn:x-inspire:specification:gmlas:Network:3.2" xmlns:tn="urn:x-inspire:specification:gmlas:CommonTransportElements:3.0" xmlns:tn-ro="urn:x-inspire:specification:gmlas:RoadTransportNetwork:3.0" xmlns:gco="http://www.isotc211.org/2005/gco" xmlns:xlink="http://www.w3.org/1999/xlink" xmlns:base="urn:x-inspire:specification:gmlas:BaseTypes:3.2" xmlns:gmd="http://www.isotc211.org/2005/gmd" xmlns:gsr="http://www.isotc211.org/2005/gsr" xmlns:gts="http://www.isotc211.org/2005/gts" xmlns:gss="http://www.isotc211.org/2005/gss" xmlns:xsi="http://www.w3.org/2001/XMLSchema-instance" xsi:schemaLocation="urn:x-inspire:specification:gmlas:BaseTypes:3.2 http://inspire.ec.europa.eu/schemas/base/3.2/BaseTypes.xsd                                 urn:x-inspire:specification:gmlas:Network:3.2 http://inspire.ec.europa.eu/schemas/net/3.2/Network.xsd                                 urn:x-inspire:specification:gmlas:CommonTransportElements:3.0 http://inspire.ec.europa.eu/schemas/tn/3.0/CommonTransportElements.xsd                                 urn:x-inspire:specification:gmlas:RoadTransportNetwork:3.0 http://inspire.ec.europa.eu/schemas/tn-ro/3.0/RoadTransportNetwork.xsd                                 urn:x-inspire:specification:gmlas:GeographicalNames:3.0 http://inspire.ec.europa.eu/schemas/gn/3.0/GeographicalNames.xsd" gml:id="NL.RWS.NWB.TN_RO.{fme:get-attribute("gid")}">
        <gml:identifier codeSpace="http://inspire.jrc.ec.europa.eu/">
                 urn:x-inspire:object:id:NL.RWS.NWB.TN-RO.Road.{fme:get-attribute('gid')}
        </gml:identifier>
        <net:beginLifespanVersion>{fme:get-attribute("wvk_begdat")}</net:beginLifespanVersion>
        <net:inspireId>
          <base:Identifier>
            <base:localId>{fme:get-attribute('gid')}</base:localId>
            <base:namespace>NL.RWS.NWB.TN-RO.Road</base:namespace>
            <base:versionId>0</base:versionId>
          </base:Identifier>
        </net:inspireId>
        <net:endLifespanVersion nilReason="other:unpopulated" xsi:nil="true"></net:endLifespanVersion>
        <net:inNetwork owns="false" nilReason="" gml:remoteSchema="" xlink:type="simple" xlink:href="" xlink:role="none" xlink:arcrole="none" xlink:title="" xlink:show="none" xlink:actuate="none"/>
        <net:link nilReason="" gml:remoteSchema="" xlink:type="simple" xlink:href="#NL.RWS.NWB.TN-RL.RoadLink.{fme:get-attribute('gid')}" xlink:role="none" xlink:arcrole="none" xlink:title="" xlink:show="none" xlink:actuate="none" owns="false"/>
        <tn:geographicalName>
          <gn:GeographicalName>
            <gn:language>NL</gn:language>
            <gn:nativeness>endonym</gn:nativeness>
            <gn:nameStatus nilReason="other:unpopulated" xsi:nil="true"></gn:nameStatus>
            <gn:sourceOfName>RijksWaterstaat</gn:sourceOfName>
            <gn:pronunciation nilReason="other:unpopulated" xsi:nil="true"></gn:pronunciation>
            <gn:spelling>
              <gn:SpellingOfName>
                <gn:text>{fme:get-attribute("stt_naam")}</gn:text>
                <gn:script>Latn</gn:script>
                <gn:transliterationScheme nilReason="other:unpopulated" xsi:nil="true"></gn:transliterationScheme>
              </gn:SpellingOfName>
            </gn:spelling>
            <gn:grammaticalGender nilReason="other:unpopulated" xsi:nil="true"></gn:grammaticalGender>
            <gn:grammaticalNumber nilReason="other:unpopulated" xsi:nil="true"></gn:grammaticalNumber>
          </gn:GeographicalName>
        </tn:geographicalName>
        <tn:validFrom>{fme:get-attribute("wvk_begdat")}</tn:validFrom>
        <tn:validTo nilReason="other:unpopulated" xsi:nil="true"></tn:validTo>
        <tn:post owns="false" nilReason="other:unpopulated" xsi:nil="true"/>
        <tn-ro:localRoadCode>{fme:get-attribute("wegnummer")}</tn-ro:localRoadCode>
        <tn-ro:nationalRoadCode>{fme:get-attribute("wegnummer")}</tn-ro:nationalRoadCode>
       </tn-ro:Road>
    VISIBLE_QUERY_VALIDATE = No
    OUTPUT_XML_HEADER = No
    -> AttributeCreator
AttributeCreator
    ATTR_LIST = ft_type,61,gml_id,fme_basicstring:17%11:NL.RWS.NWB.TN_RO.@Value(gid),binary_object,@Value(_result)
    -> AttributeExpressionRemover
XMLTemplater_Roadlink
    RESULT_ATTRIBUTE = _result
    ROOT_QUERY_EXPR:
      <tn-ro:RoadLink xmlns:gml="http://www.opengis.net/gml/3.2" xmlns:gn="urn:x-inspire:specification:gmlas:GeographicalNames:3.0" xmlns:net="urn:x-inspire:specification:gmlas:Network:3.2" xmlns:tn="urn:x-inspire:specification:gmlas:CommonTransportElements:3.0" xmlns:tn-ro="urn:x-inspire:specification:gmlas:RoadTransportNetwork:3.0" xmlns:gco="http://www.isotc211.org/2005/gco" xmlns:xlink="http://www.w3.org/1999/xlink" xmlns:base="urn:x-inspire:specification:gmlas:BaseTypes:3.2" xmlns:gmd="http://www.isotc211.org/2005/gmd" xmlns:gsr="http://www.isotc211.org/2005/gsr" xmlns:gts="http://www.isotc211.org/2005/gts" xmlns:gss="http://www.isotc211.org/2005/gss" xmlns:xsi="http://www.w3.org/2001/XMLSchema-instance" xsi:schemaLocation="urn:x-inspire:specification:gmlas:BaseTypes:3.2 http://inspire.ec.europa.eu/schemas/base/3.2/BaseTypes.xsd                                 urn:x-inspire:specification:gmlas:Network:3.2 http://inspire.ec.europa.eu/schemas/net/3.2/Network.xsd                                 urn:x-inspire:specification:gmlas:CommonTransportElements:3.0 http://inspire.ec.europa.eu/schemas/tn/3.0/CommonTransportElements.xsd                                 urn:x-inspire:specification:gmlas:RoadTransportNetwork:3.0 http://inspire.ec.europa.eu/schemas/tn-ro/3.0/RoadTransportNetwork.xsd                                 urn:x-inspire:specification:gmlas:GeographicalNames:3.0 http://inspire.ec.europa.eu/schemas/gn/3.0/GeographicalNames.xsd" gml:id="NL.RWS.NWB.TN-RL.RoadLink.{fme:get-attribute("gid")}">
        <gml:identifier codeSpace="http://inspire.jrc.ec.europa.eu/">urn:x-inspire:object:id:NL.RWS.NWB.TN-RL.RoadLink.{fme:get-attribute('gid')}</gml:identifier>
        <net:beginLifespanVersion>{fme:get-attribute("wvk_begdat")}</net:beginLifespanVersion>
        <net:inspireId>
          <base:Identifier>
            <base:localId>{fme:get-attribute("gid")}</base:localId>
            <base:namespace>NL.RWS.NWB.TN-RL.RoadLink</base:namespace>
            <base:versionId>0</base:versionId>
          </base:Identifier>
        </net:inspireId>
        <net:endLifespanVersion nilReason="other:unpopulated" xsi:nil="true"></net:endLifespanVersion>
        <net:inNetwork owns="false" nilReason="" gml:remoteSchema="" xlink:type="simple" xlink:href="" xlink:role="none" xlink:arcrole="none" xlink:title="" xlink:show="none" xlink:actuate="none"/>
        <net:centrelineGeometry nilReason="" gml:remoteSchema="" xlink:type="simple" xlink:href="" xlink:role="none" xlink:arcrole="none" xlink:title="" xlink:show="none" xlink:actuate="none" owns="false">
          <gml:LineString srsName="urn:ogc:def:crs:EPSG::4258" srsDimension="3" gml:id="NL.RWS.NWB.TN-RL.RoadLink.{fme:get-attribute('gid')}_L">
            <gml:coordinates>{fme:get-attribute('_coordinates')}</gml:coordinates>
          </gml:LineString>
        </net:centrelineGeometry>
        <net:fictitious>false</net:fictitious>
        <net:endNode owns="false" nilReason="" gml:remoteSchema="" xlink:type="simple" xlink:href="" xlink:role="none" xlink:arcrole="none" xlink:title="" xlink:show="none" xlink:actuate="none"/>
        <net:startNode owns="false" nilReason="" gml:remoteSchema="" xlink:type="simple" xlink:href="" xlink:role="none" xlink:arcrole="none" xlink:title="" xlink:show="none" xlink:actuate="none"/>
        <tn:geographicalName>
          <gn:GeographicalName>
            <gn:language>NL</gn:language>
            <gn:nativeness>endonym</gn:nativeness>
            <gn:nameStatus nilReason="other:unpopulated" xsi:nil="true"></gn:nameStatus>
            <gn:sourceOfName>RijksWaterstaat</gn:sourceOfName>
            <gn:pronunciation nilReason="other:unpopulated" xsi:nil="true"></gn:pronunciation>
            <gn:spelling>
              <gn:SpellingOfName>
                <gn:text>{fme:get-attribute("stt_naam")}</gn:text>
                <gn:script>Latn</gn:script>
                <gn:transliterationScheme nilReason="other:unpopulated" xsi:nil="true"></gn:transliterationScheme>
              </gn:SpellingOfName>
            </gn:spelling>
            <gn:grammaticalGender nilReason="other:unpopulated" xsi:nil="true"></gn:grammaticalGender>
            <gn:grammaticalNumber nilReason="other:unpopulated" xsi:nil="true"></gn:grammaticalNumber>
          </gn:GeographicalName>
        </tn:geographicalName>
        <tn:validFrom>{fme:get-attribute("wvk_begdat")}</tn:validFrom>
        <tn:validTo nilReason="other:unpopulated" xsi:nil="true"></tn:validTo>
      </tn-ro:RoadLink>
    VISIBLE_QUERY_VALIDATE = No
    OUTPUT_XML_HEADER = No
    -> AttributeCreator_2
AttributeCreator_2
    ATTR_LIST = ft_type,67,gml_id,NL.RWS.NWB.TN_RL.@Value(gid),binary_object,@Value(_result)
    -> AttributeExpressionRemover
Tester_MAX_SNELHEID
    TEST_MODE = Automatic
    TEST_DESCRIPTION = ""
    BOOL_OP = AND
    TEST_CLAUSE:
      TEST MAX_SNELHEID ATTRIBUTE_EXISTS <Unused>
      TEST MAX_SNELHEID NOT_ATTRIBUTE_IS_EMPTY <Unused>
    PASSED -> XMLTemplater_SpeedLimit
XMLTemplater_SpeedLimit
    RESULT_ATTRIBUTE = _result
    ROOT_QUERY_EXPR:
      <tn-ro:SpeedLimit xmlns:gml="http://www.opengis.net/gml/3.2" xmlns:gts="http://www.isotc211.org/2005/gts" xmlns:gsr="http://www.isotc211.org/2005/gsr" xmlns:gco="http://www.isotc211.org/2005/gco" xmlns:gmd="http://www.isotc211.org/2005/gmd" xmlns:gn="urn:x-inspire:specification:gmlas:GeographicalNames:3.0" xmlns:xlink="http://www.w3.org/1999/xlink" xmlns:gss="http://www.isotc211.org/2005/gss" xmlns:net="urn:x-inspire:specification:gmlas:Network:3.2" xmlns:tn-ro="urn:x-inspire:specification:gmlas:RoadTransportNetwork:3.0" xmlns:base="urn:x-inspire:specification:gmlas:BaseTypes:3.2" xmlns:tn="urn:x-inspire:specification:gmlas:CommonTransportElements:3.0" gml:id="NL.RWS.NWB.TN-RO.SpeedLimit.11515657">
        <gml:identifier codeSpace="http://inspire.jrc.ec.europa.eu/">
                 urn:x-inspire:object:id:NL.RWS.NWB.TN-RO.SpeedLimit.{fme:get-attribute('gid')}
        </gml:identifier>
        <gml:boundedBy  xsi:nil="true" nilReason="other:unpopulated"/>
        <net:networkRef  xsi:nil="true" nilReason="other:unpopulated"/>
        <net:inspireId>
          <base:Identifier>
            <base:localId>{fme:get-attribute('gid')}</base:localId>
            <base:namespace>NL.RWS.NWB.TN-RO.SpeedLimit</base:namespace>
            <base:versionId>0</base:versionId>
          </base:Identifier>
        </net:inspireId>
        <net:beginLifespanVersion nilReason="">{fme:get-attribute("wvk_begdat")}</net:beginLifespanVersion>
        <net:endLifespanVersion xmlns:xsi="http://www.w3.org/2001/XMLSchema-instance" nilReason="other:unpopulated" xsi:nil="true"/>
        <tn:validFrom>{fme:get-attribute("wvk_begdat")}</tn:validFrom>
        <tn:validTo xmlns:xsi="http://www.w3.org/2001/XMLSchema-instance" nilReason="other:unpopulated" xsi:nil="true"/>
        <tn-ro:areaCondition nilReason="other:unpopulated" codeSpace=""/>
        <tn-ro:direction nilReason="" codeSpace=""/>
        <tn-ro:laneExtension xsi:nil="true" nilReason="other:unpopulated"/>
        <tn-ro:speedLimitMinMaxType>maximum</tn-ro:speedLimitMinMaxType>
        <tn-ro:speedLimitSource nilReason="" codeSpace="">RijksWaterStaat</tn-ro:speedLimitSource>
        <tn-ro:speedLimitValue uom="km">{fme:get-attribute("MAX_SNELHEID")}</tn-ro:speedLimitValue>
        <tn-ro:startLane xsi:nil="true" nilReason="other:unpopulated"/>
        <tn-ro:validityPeriod nilReason="other:unpopulated"/>
        <tn-ro:vehicleType nilReason="other:unpopulated" codeSpace=""/>
        <tn-ro:weatherCondition nilReason="other:unpopulated" codeSpace=""/>
      </tn-ro:SpeedLimit>
    VISIBLE_QUERY_VALIDATE = No
    OUTPUT_XML_HEADER = No
    -> AttributeCreator_4
AttributeCreator_4
    ATTR_LIST = ft_type,98,gml_id,NL.RWS.NWB.TN_SL.@Value(gid),binary_object,@Value(_result)
    -> AttributeExpressionRemover
Tester_RIJSTROKEN
    TEST_MODE = Automatic
    TEST_DESCRIPTION = ""
    BOOL_OP = AND
    TEST_CLAUSE:
      TEST RIJSTROKEN ATTRIBUTE_EXISTS <Unused>
      TEST RIJSTROKEN NOT_ATTRIBUTE_IS_EMPTY <Unused>
    PASSED -> SubstringExtractor
SubstringExtractor
    RESULT_ATTR = rijstroken1
    SRC_ATTR = RIJSTROKEN
    START = 0
    END = 0
    -> SubstringExtractor_2
SubstringExtractor_2
    RESULT_ATTR = rijstroken2
    SRC_ATTR = RIJSTROKEN
    START = -1
    END = -1
    -> Tester
Tester
    TEST_MODE = Automatic
    TEST_DESCRIPTION = ""
    BOOL_OP = OR
    TEST_CLAUSE = TEST @Value(rijstroken1) > @Value(rijstroken2)
    PASSED -> AttributeCreator_5
    FAILED -> AttributeCreator_6
AttributeCreator_5
    ATTR_LIST = rijstroken_max,@Value(rijstroken1),rijstroken_min,@Value(rijstroken2)
    -> XMLTemplater_NumberOfLanes_max
    -> XMLTemplater_NumberOfLanes_min
AttributeCreator_6
    ATTR_LIST = rijstroken_max,@Value(rijstroken2),rijstroken_min,@Value(rijstroken1)
    -> XMLTemplater_NumberOfLanes_min
    -> XMLTemplater_NumberOfLanes_max
XMLTemplater_NumberOfLanes_max
    RESULT_ATTRIBUTE = _result
    ROOT_QUERY_EXPR:
      <tn-ro:NumberOfLanes xmlns:gml="http://www.opengis.net/gml/3.2" xmlns:gts="http://www.isotc211.org/2005/gts" xmlns:gsr="http://www.isotc211.org/2005/gsr" xmlns:gco="http://www.isotc211.org/2005/gco" xmlns:gmd="http://www.isotc211.org/2005/gmd" xmlns:gn="urn:x-inspire:specification:gmlas:GeographicalNames:3.0" xmlns:xlink="http://www.w3.org/1999/xlink" xmlns:gss="http://www.isotc211.org/2005/gss" xmlns:net="urn:x-inspire:specification:gmlas:Network:3.2" xmlns:tn-ro="urn:x-inspire:specification:gmlas:RoadTransportNetwork:3.0" xmlns:base="urn:x-inspire:specification:gmlas:BaseTypes:3.2" xmlns:tn="urn:x-inspire:specification:gmlas:CommonTransportElements:3.0" gml:id="NL.RWS.NWB.TN_RO.12242147.min">
        <gml:identifier codeSpace="http://inspire.jrc.ec.europa.eu/">
                 urn:x-inspire:object:id:NL.RWS.NWB.TN-RO.NumberOfLanes.max.{fme:get-attribute('gid')}
        </gml:identifier>
        <gml:boundedBy  xsi:nil="true" nilReason="other:unpopulated"/>
        <net:networkRef  xsi:nil="true" nilReason="other:unpopulated"/>
        <net:inspireId>
          <base:Identifier>
            <base:localId>max.{fme:get-attribute('gid')}</base:localId>
            <base:namespace>NL.RWS.NWB.TN-RO.NumberOfLanes</base:namespace>
            <base:versionId>0</base:versionId>
          </base:Identifier>
        </net:inspireId>
        <net:beginLifespanVersion nilReason="">{fme:get-attribute("wvk_begdat")}</net:beginLifespanVersion>
        <net:endLifespanVersion xmlns:xsi="http://www.w3.org/2001/XMLSchema-instance" nilReason="other:unpopulated" xsi:nil="true"/>
        <tn:validFrom>{fme:get-attribute("wvk_begdat")}</tn:validFrom>
        <tn:validTo xmlns:xsi="http://www.w3.org/2001/XMLSchema-instance" nilReason="other:unpopulated" xsi:nil="true"/>
        <tn-ro:direction nilReason="" codeSpace=""/>
        <tn-ro:minMaxNumberOfLanes>maximum</tn-ro:minMaxNumberOfLanes>
        <tn-ro:numberOfLanes>{fme:get-attribute("rijstroken_max")}</tn-ro:numberOfLanes>
      </tn-ro:NumberOfLanes>
    VISIBLE_QUERY_VALIDATE = No
    OUTPUT_XML_HEADER = No
    -> AttributeCreator_3
AttributeCreator_3
    ATTR_LIST = ft_type,99,gml_id,NL.RWS.NWB.TN_RN.max.@Value(gid),binary_object,@Value(_result)
    -> AttributeExpressionRemover
XMLTemplater_NumberOfLanes_min
    RESULT_ATTRIBUTE = _result
    ROOT_QUERY_EXPR:
      <tn-ro:NumberOfLanes xmlns:gml="http://www.opengis.net/gml/3.2" xmlns:gts="http://www.isotc211.org/2005/gts" xmlns:gsr="http://www.isotc211.org/2005/gsr" xmlns:gco="http://www.isotc211.org/2005/gco" xmlns:gmd="http://www.isotc211.org/2005/gmd" xmlns:gn="urn:x-inspire:specification:gmlas:GeographicalNames:3.0" xmlns:xlink="http://www.w3.org/1999/xlink" xmlns:gss="http://www.isotc211.org/2005/gss" xmlns:net="urn:x-inspire:specification:gmlas:Network:3.2" xmlns:tn-ro="urn:x-inspire:specification:gmlas:RoadTransportNetwork:3.0" xmlns:base="urn:x-inspire:specification:gmlas:BaseTypes:3.2" xmlns:tn="urn:x-inspire:specification:gmlas:CommonTransportElements:3.0" gml:id="NL.RWS.NWB.TN_RO.12242147.min">
        <gml:identifier codeSpace="http://inspire.jrc.ec.europa.eu/">
                 urn:x-inspire:object:id:NL.RWS.NWB.TN-RO.NumberOfLanes.min.{fme:get-attribute('gid')}
        </gml:identifier>
        <gml:boundedBy  xsi:nil="true" nilReason="other:unpopulated"/>
        <net:networkRef  xsi:nil="true" nilReason="other:unpopulated"/>
        <net:inspireId>
          <base:Identifier>
            <base:localId>min.{fme:get-attribute('gid')}</base:localId>
            <base:namespace>NL.RWS.NWB.TN-RO.NumberOfLanes</base:namespace>
            <base:versionId>0</base:versionId>
          </base:Identifier>
        </net:inspireId>
        <net:beginLifespanVersion nilReason="">{fme:get-attribute("wvk_begdat")}</net:beginLifespanVersion>
        <net:endLifespanVersion xmlns:xsi="http://www.w3.org/2001/XMLSchema-instance" nilReason="other:unpopulated" xsi:nil="true"/>
        <tn:validFrom>{fme:get-attribute("wvk_begdat")}</tn:validFrom>
        <tn:validTo xmlns:xsi="http://www.w3.org/2001/XMLSchema-instance" nilReason="other:unpopulated" xsi:nil="true"/>
        <tn-ro:direction nilReason="" codeSpace=""/>
        <tn-ro:minMaxNumberOfLanes>minimum</tn-ro:minMaxNumberOfLanes>
        <tn-ro:numberOfLanes>{fme:get-attribute("rijstroken_min")}</tn-ro:numberOfLanes>
      </tn-ro:NumberOfLanes>
    VISIBLE_QUERY_VALIDATE = No
    OUTPUT_XML_HEADER = No
    -> AttributeCreator_7
AttributeCreator_7
    ATTR_LIST = ft_type,99,gml_id,NL.RWS.NWB.TN_RN.min.@Value(gid),binary_object,@Value(_result)
    -> AttributeExpressionRemover
AttributeExpressionRemover
    ATTR_EXP = post*
    -> BinaryEncoder
BinaryEncoder
    ENCODING_TYPE = HEX
    ATTR_TO_ENCODE = binary_object
    DEST_ATTR = binary_object
    -> 2DForcer
2DForcer
    2D -> inspire_tn.gml_objects (writer POSTGIS_2)
inspire_tn.gml_objects (writer POSTGIS_2)
    attributes: id serial,PRIKEY, gml_id text,none, ft_type int2, binary_object bytea
