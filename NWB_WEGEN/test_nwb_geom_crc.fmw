FME workspace test_nwb_geom_crc.fmw

Parameters:
- MAX_FEATURES =   # Max Features to Read
- SourceDataset_SHAPE = ""$(FME_MF_DIR)Scripts2PG\Data\max_snelheden.shp" "$(FME_MF_DIR)Scripts2PG\Data\rijstroken.shp""   # Source Esri Shape File(s)

Readers:
- POSTGIS_1: POSTGIS from pdok
- SHAPE_1: SHAPE from $(SourceDataset_SHAPE)

nwbwegen.wegvakken_imp (reader POSTGIS_1)
    attributes: gid serial,PRIKEY, wvk_id float8, wvk_begdat date, jte_id_beg float8, jte_id_end float8, wegbehsrt varchar(1), wegnummer varchar(5), wegdeelltr varchar(1), hecto_lttr varchar(1), baansubsrt varchar(3), rpe_code varchar(2), admrichtng varchar(1), rijrichtng varchar(1), stt_naam varchar(29), wpsnaamnen varchar(24), gme_id int2, gme_naam varchar(24), hnrstrlnks varchar(1), hnrstrrhts varchar(1), e_hnr_lnks int4, e_hnr_rhts int4, l_hnr_lnks int4, l_hnr_rhts int4, begafstand int4, endafstand int4, beginkm float8, eindkm float8, pos_tv_wol varchar(1), geom_valid bool
    -> AttributeKeeper
AttributeKeeper
    KEEP_ATTRS = wvk_id
    -> AttributeCopier
AttributeCopier
    ATTR_LIST = WVK_ID,wvk_id
    -> CoordinateRounder
CoordinateRounder
    ZPREC = 0
    YPREC = 0
    XPREC = 0
    ROUNDED -> CRCCalculator
CRCCalculator
    CRC_CHOICES = Coordinates and Attributes
    CRC_ATTR = _crc
    CALC_ATTRS = wvk_id
    -> rijstroken [input 1]
    -> snelheden [input 1]
rijstroken (reader SHAPE_1)
    attributes: OMSCHR char(40), VOLGNRSTRK char(3), KANTCODE char(1), WVK_ID number(10,0), WVK_BEGDAT date, BEGAFSTAND number(8,0), ENDAFSTAND number(8,0), FK_VELD1 char(20), FK_VELD4 char(13), IZI_SIDE char(1), SHAPE_LEN number(19,11)
    -> AttributeKeeper_2
AttributeKeeper_2
    KEEP_ATTRS = OMSCHR,WVK_ID
    -> CoordinateRounder_2
CoordinateRounder_2
    ZPREC = 0
    YPREC = 0
    XPREC = 0
    ROUNDED -> CRCCalculator_2
CRCCalculator_2
    CRC_CHOICES = Coordinates and Attributes
    CRC_ATTR = _crc
    CALC_ATTRS = WVK_ID
    -> rijstroken [input 2]
rijstroken: ChangeDetector
    MATCHATTRS = _crc
    MATCH = NONE
    MATCH_STRATEGY = Match Selected Attributes
    LENIENT_MATCH = Yes
    BLANK_AND_MISSING_DIFFER = No
    UNCHANGED -> rijstroken_UNCHANGED
    ADDED -> rijstroken_ADDED
    DELETED -> rijstroken_DELETED
rijstroken_UNCHANGED: Inspector
rijstroken_ADDED: Inspector
rijstroken_DELETED: Inspector
max_snelheden (reader SHAPE_1)
    attributes: OMSCHR number(8,0), KANTCODE char(1), WVK_ID number(10,0), WVK_BEGDAT date, BEGAFSTAND number(8,0), ENDAFSTAND number(8,0), FK_VELD1 char(20), FK_VELD4 char(13), IZI_SIDE char(1), SHAPE_LEN number(19,11)
    -> AttributeKeeper_3
AttributeKeeper_3
    KEEP_ATTRS = OMSCHR,WVK_ID
    -> CoordinateRounder_3
CoordinateRounder_3
    ZPREC = 0
    YPREC = 0
    XPREC = 0
    ROUNDED -> CRCCalculator_3
CRCCalculator_3
    CRC_CHOICES = Coordinates and Attributes
    CRC_ATTR = _crc
    CALC_ATTRS = WVK_ID
    -> snelheden [input 2]
snelheden: ChangeDetector
    MATCHATTRS = _crc
    MATCH = NONE
    MATCH_STRATEGY = Match Selected Attributes
    LENIENT_MATCH = Yes
    BLANK_AND_MISSING_DIFFER = No
    UNCHANGED -> snelheden_UNCHANGED
    ADDED -> snelheden_ADDED
    DELETED -> snelheden_DELETED
snelheden_UNCHANGED: Inspector
snelheden_ADDED: Inspector
snelheden_DELETED: Inspector
