FME workspace test_nwb_id.fmw

Parameters:
- MAX_FEATURES =   # Max Features to Read
- SourceDataset_SHAPE = ""$(FME_MF_DIR)Scripts2PG\Data\max_snelheden.shp" "$(FME_MF_DIR)Scripts2PG\Data\rijstroken.shp""   # Source Esri Shape File(s)

Readers:
- POSTGIS_1: POSTGIS from pdok
- SHAPE_1: SHAPE from $(SourceDataset_SHAPE)

Writers:
- NULL_1: NULL to <Unused>

nwbwegen.wegvakken_imp (reader POSTGIS_1)
    attributes: gid serial,PRIKEY, wvk_id float8, wvk_begdat date, jte_id_beg float8, jte_id_end float8, wegbehsrt varchar(1), wegnummer varchar(5), wegdeelltr varchar(1), hecto_lttr varchar(1), baansubsrt varchar(3), rpe_code varchar(2), admrichtng varchar(1), rijrichtng varchar(1), stt_naam varchar(29), wpsnaamnen varchar(24), gme_id int2, gme_naam varchar(24), hnrstrlnks varchar(1), hnrstrrhts varchar(1), e_hnr_lnks int4, e_hnr_rhts int4, l_hnr_lnks int4, l_hnr_rhts int4, begafstand int4, endafstand int4, beginkm float8, eindkm float8, pos_tv_wol varchar(1), geom_valid bool
    -> AttributeKeeper
AttributeKeeper
    KEEP_ATTRS = wvk_id
    -> AttributeCopier
AttributeCopier
    ATTR_LIST = WVK_ID,wvk_id
    -> Rijstroken_FeatureMerger [input 1]
    -> Snelheden_FeatureMerger [input 1]
rijstroken (reader SHAPE_1)
    attributes: OMSCHR char(40), VOLGNRSTRK char(3), KANTCODE char(1), WVK_ID number(10,0), WVK_BEGDAT date, BEGAFSTAND number(8,0), ENDAFSTAND number(8,0), FK_VELD1 char(20), FK_VELD4 char(13), IZI_SIDE char(1), SHAPE_LEN number(19,11)
    -> AttributeKeeper_2
AttributeKeeper_2
    KEEP_ATTRS = OMSCHR,WVK_ID
    -> Rijstroken_FeatureMerger [input 2]
Rijstroken_FeatureMerger: FeatureMerger
    BUILD_INCOMPLETE = Yes
    PROCESS_DUPS = No
    MERGE_TYPE = Attributes Only
    REFERATTR = WVK_ID
    REFEEATTR = WVK_ID
    COMPLETE -> Rijstroken_complete (writer NULL_1)
    INCOMPLETE -> Rijstroken_incomplete (writer NULL_1)
    UNREFERENCED -> Rijstroken_unreferenced (writer NULL_1)
Rijstroken_complete (writer NULL_1)
Rijstroken_incomplete (writer NULL_1)
Rijstroken_unreferenced (writer NULL_1)
max_snelheden (reader SHAPE_1)
    attributes: OMSCHR number(8,0), KANTCODE char(1), WVK_ID number(10,0), WVK_BEGDAT date, BEGAFSTAND number(8,0), ENDAFSTAND number(8,0), FK_VELD1 char(20), FK_VELD4 char(13), IZI_SIDE char(1), SHAPE_LEN number(19,11)
    -> AttributeKeeper_3
AttributeKeeper_3
    KEEP_ATTRS = OMSCHR,WVK_ID
    -> Snelheden_FeatureMerger [input 2]
Snelheden_FeatureMerger: FeatureMerger
    BUILD_INCOMPLETE = Yes
    PROCESS_DUPS = No
    MERGE_TYPE = Attributes Only
    REFERATTR = WVK_ID
    REFEEATTR = WVK_ID
    COMPLETE -> Snelheden_complete (writer NULL_1)
    INCOMPLETE -> Snelheden_incomplete (writer NULL_1)
    UNREFERENCED -> Snelheden_unreferenced (writer NULL_1)
Snelheden_complete (writer NULL_1)
Snelheden_incomplete (writer NULL_1)
Snelheden_unreferenced (writer NULL_1)
