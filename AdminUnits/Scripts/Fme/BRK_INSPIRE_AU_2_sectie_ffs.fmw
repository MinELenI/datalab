FME workspace BRK_INSPIRE_AU_2_sectie_ffs.fmw

Parameters:
- SourceDataset_FFS = D:\Projects\PDOK\AdminUnits\Scripts\Ffs\Percelen\AAL01.ffs   # Source FME Feature Store (FFS) File(s)
- UITVOER_DIRECTORY = D:\Projects\PDOK\AdminUnits\Scripts\Ffs\Secties   # Fanout Directory
- LOG_FILE =   # Log File

Readers:
- FFS_1: FFS from $(SourceDataset_FFS)

Writers:
- FFS_2: FFS to D:\Projects\PDOK\AdminUnits\Scripts\Ffs\Sectie.ffs

perceelgrenzen (reader FFS_1)
    attributes: gid int32, kadgem varchar(5), kadgem_sectie varchar(7), perceelnr varchar(17), geom_valid logical
    -> Dissolver
Dissolver
    GROUP_BY = kadgem kadgem_sectie
    NO_OVRLP = Yes
    ACCUM_INPUT_ATTRS = No
    AREA -> secties (writer FFS_2)
secties (writer FFS_2)
    attributes: kadgem varchar(5), kadgem_sectie varchar(7)
