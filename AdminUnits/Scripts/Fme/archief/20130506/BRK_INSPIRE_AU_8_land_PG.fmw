FME workspace BRK_INSPIRE_AU_8_land_PG.fmw

Parameters:
- SourceDataset_FFS = D:\Projects\PDOK\AdminUnits\Scripts\Ffs\Gemeenten\provincie.ffs   # Source FME Feature Store (FFS) File(s)
- LOG_FILE = ..\log\test.log   # Log File

Readers:
- FFS_1: FFS from $(SourceDataset_FFS)

Writers:
- POSTGIS_1: POSTGIS to pdok

Provincie (reader FFS_1)
    attributes: provincie varchar(100)
    -> Dissolver
Dissolver
    NO_OVRLP = No
    ACCUM_INPUT_ATTRS = No
    AREA -> CsmapReprojector
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> AttributeCreator
AttributeCreator
    ATTR_LIST = gml_id,NL.KAD.BRK.AdministrativeUnit.Nederland,ft_type,18,Namespace,NL.KAD.BRK.AdministrativeUnit,Naam,Nederland
    -> DonutHoleExtractor
DonutHoleExtractor
    OUTERSHELL -> Orientor
Orientor
    KIND = RIGHT_HAND_RULE
    ORIENTED -> CoordinateSwapper
Note: Omkeren volgorde lat en lon voor GML
CoordinateSwapper
    SWAP_TYPE = X <-> Y
    -> CoordinateConcatenator
CoordinateConcatenator
    COORD_ATTR = exterior
    COORD_DELIM = " "
    COORDINATES_TO_INCLUDE_DIS = X Y
    ELEMENT_DELIM = " "
    -> Tester
Tester
    TEST_MODE = Automatic
    TEST_DESCRIPTION = ""
    BOOL_OP = OR
    TEST_CLAUSE = TEST @Area() > 1
    PASSED -> XMLTemplater_poly
XMLTemplater_poly
    RESULT_ATTRIBUTE = binary_object
    ROOT_QUERY_EXPR:
      <au:AdministrativeUnit xmlns:gts="http://www.isotc211.org/2005/gts"
                             xmlns:xlink="http://www.w3.org/1999/xlink"
                             xmlns:xsi="http://www.w3.org/2001/XMLSchema-instance"
                             xmlns:gss="http://www.isotc211.org/2005/gss"
                             xmlns:gco="http://www.isotc211.org/2005/gco"
                             xmlns:gsr="http://www.isotc211.org/2005/gsr"
                             xmlns:au="urn:x-inspire:specification:gmlas:AdministrativeUnits:3.0"
                             xmlns:stat="urn:x-inspire:specification:gmlas:StatisticalUnits:0.0"
                             xmlns:base="urn:x-inspire:specification:gmlas:BaseTypes:3.2"
                             xmlns:gml="http://www.opengis.net/gml/3.2"
                             xmlns:gmd="http://www.isotc211.org/2005/gmd"
                             xmlns:gn="urn:x-inspire:specification:gmlas:GeographicalNames:3.0"
                             gml:id="{fme:get-attribute("gml_id")}">
        <gml:identifier codeSpace=""></gml:identifier>
        <au:geometry nilReason="" gml:remoteSchema="" xlink:type="simple" xlink:href="" xlink:role="none" xlink:arcrole="none" xlink:title="none" xlink:show="none" xlink:actuate="none" owns="false">
              <gml:MultiSurface gml:id="MultiSurface_{fme:get-attribute("Naam")}" srsName="urn:ogc:def:crs:EPSG::4258">
                <gml:surfaceMember>
                  <gml:Surface gml:id="Surface_{fme:get-attribute("Naam")}" srsName="urn:ogc:def:crs:EPSG::4258">
                    <gml:patches>
                      <gml:PolygonPatch interpolation="planar">
                        <gml:exterior>
                          <gml:LinearRing>
                            <gml:posList srsName="urn:ogc:def:crs:EPSG::4258" srsDimension="2">{fme:get-attribute("exterior")}</gml:posList>
                          </gml:LinearRing>
                        </gml:exterior>
                      </gml:PolygonPatch>
                    </gml:patches>
                  </gml:Surface>
                </gml:surfaceMember>
              </gml:MultiSurface>
        </au:geometry>
        <au:nationalCode>{fme:get-attribute("Naam")}</au:nationalCode>
        <au:inspireId>
          <base:Identifier>
            <base:localId>{fme:get-attribute("Naam")}</base:localId>
            <base:namespace>{fme:get-attribute("Namespace")}</base:namespace>
            <base:versionId nilReason="">0</base:versionId>
          </base:Identifier>
        </au:inspireId>
        <au:nationalLevel codeSpace="urn:x-inspire:specification:gmlas:AdministrativeUnits:3.0/AdministrativeHierarchyLevel">1stOrder</au:nationalLevel>
        <au:nationalLevelName>
          <gmd:LocalisedCharacterString id="_25289_44036" locale="NL">land</gmd:LocalisedCharacterString>
        </au:nationalLevelName>
        <au:country>
          <gmd:Country codeList="CountryCode" codeListValue="NL" codeSpace="urn:x-inspire:specification:gmlas:BaseTypes:3.2/CountryCode">NL</gmd:Country>
        </au:country>
        <au:name>
          <gn:GeographicalName>
            <gn:language>NL</gn:language>
            <gn:nativeness>endonym</gn:nativeness>
            <gn:nameStatus  nilReason="other:unpopulated" xsi:nil="true"></gn:nameStatus>
            <gn:sourceOfName>Kadaster</gn:sourceOfName>
            <gn:pronunciation nilReason="other:unpopulated" xsi:nil="true"/>
            <gn:spelling>
              <gn:SpellingOfName>
                <gn:text>{fme:get-attribute("Naam")}</gn:text>
                  <gn:script>Latn</gn:script>
              </gn:SpellingOfName>
            </gn:spelling>
          </gn:GeographicalName>
        </au:name>
        <au:residenceOfAuthority xsi:nil="true" nilReason="other:unpopulated"></au:residenceOfAuthority>
        <au:beginLifespanVersion xsi:nil="true" nilReason="other:unpopulated"></au:beginLifespanVersion>
        <au:endLifespanVersion xsi:nil="true" nilReason="other:unpopulated"></au:endLifespanVersion>
        <au:NUTS xsi:nil="true" nilReason="other:unpopulated"/>
        <au:condominium xsi:nil="true" nilReason="other:unpopulated"/>
        <au:boundary  xsi:nil="true" nilReason="other:unpopulated"/>
      </au:AdministrativeUnit>
    VISIBLE_QUERY_VALIDATE = No
    OUTPUT_XML_HEADER = No
    -> StringReplacer
Note: Maken binary_object voor postgres database
StringReplacer
    SRC_ATTRS = binary_object
    REGEXP = no
    CASE = no
    REPLACE_TEXT = " "
    FIND_TEXT = xmlns:gts="http://www.isotc211.org/2005/gts"                         xmlns:xlink="http://www.w3.org/1999/xlink"                         xmlns:xsi="http://www.w3.org/2001/XMLSchema-instance"                         xmlns:gss="http://www.isotc211.org/2005/gss"                         xmlns:gco="http://www.isotc211.org/2005/gco"                         xmlns:gsr="http://www.isotc211.org/2005/gsr"                         xmlns:au="urn:x-inspire:specification:gmlas:AdministrativeUnits:3.0"                         xmlns:stat="urn:x-inspire:specification:gmlas:StatisticalUnits:0.0"                         xmlns:base="urn:x-inspire:specification:gmlas:BaseTypes:3.2"                         xmlns:gml="http://www.opengis.net/gml/3.2"                         xmlns:gmd="http://www.isotc211.org/2005/gmd"                         xmlns:gn="urn:x-inspire:specification:gmlas:GeographicalNames:3.0"
    -> BinaryEncoder
BinaryEncoder
    ENCODING_TYPE = HEX
    ATTR_TO_ENCODE = binary_object
    DEST_ATTR = binary_object
    -> BoundingBoxReplacer
Note: Maken bounding box geometrie
BoundingBoxReplacer
    BOXTYPE = Bounding Box
    BOX -> AttributeExpressionRemover_3
Note: Verwijderen alle originele / postgres attributen
AttributeExpressionRemover_3
    ATTR_EXP = postgis*
    -> CoordinateSwapper_3
CoordinateSwapper_3
    SWAP_TYPE = X <-> Y
    -> inspire_au.gml_objects (writer POSTGIS_1)
inspire_au.gml_objects (writer POSTGIS_1)
    attributes: id serial,PRIKEY, gml_id text,none, ft_type int2, binary_object bytea

FME custom transformer GUIDGenerator
Creates an ESRI GUID ID by creating a UUID and concatenating {} to it.
This custom transformer will add a GFID attribute to input features.
Copyright (c) 2012 Safe Software Inc.
Permission is granted to anyone, free of charge, to use, modify and distribute the object code form of this transformer for any purpose, subject to the following restrictions:
1) The origin of this transformer and associated FME(R) software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

INPUT (input)
    -> UUIDGENERATOR_2
UUIDGENERATOR_2: UUIDGenerator
    UUID_ATTR = GFID
    -> CONCATENATOR_2
CONCATENATOR_2: Concatenator
    PARM_LINE = {,&GFID,}
    VAL_ATTR = GFID
    PARM_LINE_TCL = "\{" [FME_GetAttribute {GFID}] "\}"
    -> OUTPUT (output)
OUTPUT (output)
