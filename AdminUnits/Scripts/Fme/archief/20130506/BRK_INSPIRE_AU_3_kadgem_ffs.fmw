FME workspace BRK_INSPIRE_AU_3_kadgem_ffs.fmw

Parameters:
- SourceDataset_FFS = D:\Projects\PDOK\AdminUnits\Scripts\Ffs\Secties\*.ffs   # Source FME Feature Store (FFS) File(s)
- DestDataset_FFS = D:\Projects\PDOK\AdminUnits\Scripts\Ffs\Gemeente\kadgem.ffs   # Destination FME Feature Store (FFS) File
- LOG_FILE =   # Log File

Readers:
- FFS_1: FFS from $(SourceDataset_FFS)

Writers:
- FFS_2: FFS to $(DestDataset_FFS)

secties (reader FFS_1)
    attributes: kadgem varchar(5), kadgem_sectie varchar(7)
    -> Dissolver
Dissolver
    GROUP_BY = kadgem
    NO_OVRLP = Yes
    ACCUM_INPUT_ATTRS = No
    AREA -> Aggregator
Aggregator
    GROUP_BY = kadgem
    MODE = Assemble One Level
    ACCUM_ATTRS_NAME = No
    SEP = ,
    AGGREGATE_TYPE = Homogeneous Collection (If Possible)
    ORDERED = No
    AGGREGATE -> Kadgem (writer FFS_2)
Kadgem (writer FFS_2)
    attributes: kadgem varchar(5)
