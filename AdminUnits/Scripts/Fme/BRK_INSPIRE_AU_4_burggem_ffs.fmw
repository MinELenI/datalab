FME workspace BRK_INSPIRE_AU_4_burggem_ffs.fmw

Parameters:
- SourceDataset_FFS = D:\Projects\PDOK\AdminUnits\Scripts\Ffs\Gemeente\kadgem.ffs   # Source FME Feature Store (FFS) File(s)
- SourceDataset_XLS_ADO = D:\Projects\PDOK\AdminUnits\Scripts\Data\XD720_2013.xls   # Source Microsoft Excel File(s)
- SourceDataset_TEXTLINE = D:\Projects\PDOK\AdminUnits\Scripts\Data\FINGIS_BURG_PROV.txt   # Source Text File(s)
- DestDataset_FFS_BurgGem = D:\Projects\PDOK\AdminUnits\Scripts\Ffs\Gemeente\burggem.ffs   # Destination FME Feature Store (FFS) File
- DestDataset_FFS_Prov = D:\Projects\PDOK\AdminUnits\Scripts\Ffs\Gemeente\provincie.ffs   # Destination FME Feature Store (FFS) File
- LOG_FILE =   # Log File

Readers:
- FFS_1: FFS from $(SourceDataset_FFS)
- XLS_ADO_1: XLS_ADO from $(SourceDataset_XLS_ADO)
- TEXTLINE_1: TEXTLINE from $(SourceDataset_TEXTLINE)

Writers:
- FFS_2: FFS to $(DestDataset_FFS_BurgGem)
- FFS_3: FFS to $(DestDataset_FFS_Prov)

Kadgem (reader FFS_1)
    attributes: kadgem varchar(5)
    -> FeatureMerger [input 1]
Blad1 (reader XLS_ADO_1)
    attributes: Kad_gem_code varchar(255), Kad_naam varchar(255), Burg_nr varchar(255), Burg_gem_code varchar(255), Burg_naam varchar(255), Bew_code varchar(255), Bew_naam varchar(255)
    -> FeatureMerger [input 2]
FeatureMerger
    BUILD_INCOMPLETE = No
    PROCESS_DUPS = No
    MERGE_TYPE = Attributes Only
    REFERATTR = kadgem
    REFEEATTR = Kad_gem_code
    COMPLETE -> Dissolver
Dissolver
    GROUP_BY = Burg_nr Burg_gem_code Burg_naam
    NO_OVRLP = No
    ACCUM_INPUT_ATTRS = No
    AREA -> FeatureMerger_2 [input 1]
    AREA -> Aggregator_2
Aggregator_2
    GROUP_BY = Burg_nr Burg_naam
    MODE = Assemble One Level
    ACCUM_ATTRS_NAME = No
    SEP = ,
    AGGREGATE_TYPE = Homogeneous Collection (If Possible)
    ORDERED = No
    AGGREGATE -> Gemeente (writer FFS_2)
Gemeente (writer FFS_2)
    attributes: Burg_nr varchar(255), Burg_naam varchar(255)
text_line (reader TEXTLINE_1)
    attributes: text_line_data buffer
    -> SubstringExtractor
SubstringExtractor
    RESULT_ATTR = burggem
    SRC_ATTR = text_line_data
    START = 0
    END = 4
    -> SubstringExtractor_2
SubstringExtractor_2
    RESULT_ATTR = provincie
    SRC_ATTR = text_line_data
    START = 5
    END = -1
    -> FeatureMerger_2 [input 2]
FeatureMerger_2
    BUILD_INCOMPLETE = No
    PROCESS_DUPS = No
    MERGE_TYPE = Attributes Only
    REFERATTR = Burg_gem_code
    REFEEATTR = burggem
    COMPLETE -> Dissolver_2
Dissolver_2
    GROUP_BY = provincie
    NO_OVRLP = No
    ACCUM_INPUT_ATTRS = No
    AREA -> Aggregator
Aggregator
    GROUP_BY = provincie
    MODE = Assemble One Level
    ACCUM_ATTRS_NAME = No
    SEP = ,
    AGGREGATE_TYPE = Homogeneous Collection (If Possible)
    ORDERED = No
    AGGREGATE -> Provincie (writer FFS_3)
Provincie (writer FFS_3)
    attributes: provincie varchar(100)
