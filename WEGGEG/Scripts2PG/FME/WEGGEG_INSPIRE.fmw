FME workspace WEGGEG_INSPIRE.fmw

Parameters:
- SourceDataset_POSTGIS = pdok   # Source PostGIS Dataset

Readers:
- POSTGIS_1: POSTGIS from $(SourceDataset_POSTGIS)

Writers:
- POSTGIS_2: POSTGIS to pdok

Note: weggeg.max_snelheden_imp
weggeg.max_snelheden_imp (reader POSTGIS_1)
    attributes: gid serial,PRIKEY, omschr int4, beginwdl varchar(1), beginkm float8, eindwdl varchar(1), eindkm float8, kantcode varchar(1), wegnummer varchar(5), fk_veld4 varchar(13), izi_side varchar(1), geom_valid bool
    -> Reprojector
Reprojector
    DEST = EPSG:4258
    SOURCE = EPSG:28992
    RASTER_CELL_SIZE = Preserve Cells
    INTERPOLATION_TYPE_NAME = Nearest Neighbor
    STROKE_ARCS = Yes
    REPROJECTED -> CoordinateSwapper
CoordinateSwapper
    SWAP_TYPE = X <-> Y
    -> 3DForcer
3DForcer
    ZVALATTR = 0
    -> CoordinateConcatenator
CoordinateConcatenator
    COORD_ATTR = _coordinates
    COORD_DELIM = " "
    COORDINATES_TO_INCLUDE_DIS = X Y Z
    ELEMENT_DELIM = ,
    -> CoordinateSwapper_2
CoordinateSwapper_2
    SWAP_TYPE = X <-> Y
    -> StringReplacer
StringReplacer
    FIND_TEXT = "^2,[0123456789]*,0 "
    SRC_ATTRS = _coordinates
    REGEXP = yes
    CASE = no
    -> XMLTemplater
XMLTemplater
    OUTPUT_XML_HEADER = Yes
    VISIBLE_QUERY_VALIDATE = No
    ROOT_QUERY_EXPR:
      <tn-ro:SpeedLimitxmlns:gml="http://www.opengis.net/gml/3.2"
                  xmlns:gn="urn:x-inspire:specification:gmlas:GeographicalNames:3.0"
                  xmlns:net="urn:x-inspire:specification:gmlas:Network:3.2"
                  xmlns:tn="urn:x-inspire:specification:gmlas:CommonTransportElements:3.0"
                  xmlns:tn-ro="urn:x-inspire:specification:gmlas:RoadTransportNetwork:3.0"
                  xmlns:gco="http://www.isotc211.org/2005/gco"
                  xmlns:xlink="http://www.w3.org/1999/xlink"
                  xmlns:base="urn:x-inspire:specification:gmlas:BaseTypes:3.2"
                  xmlns:gmd="http://www.isotc211.org/2005/gmd" xmlns:gsr="http://www.isotc211.org/2005/gsr"
                  xmlns:gts="http://www.isotc211.org/2005/gts" xmlns:gss="http://www.isotc211.org/2005/gss"
                  xsi:schemaLocation="urn:x-inspire:specification:gmlas:BaseTypes:3.2 http://inspire.ec.europa.eu/schemas/base/3.2/BaseTypes.xsd
                                      urn:x-inspire:specification:gmlas:Network:3.2 http://inspire.ec.europa.eu/schemas/net/3.2/Network.xsd
                                      urn:x-inspire:specification:gmlas:CommonTransportElements:3.0 http://inspire.ec.europa.eu/schemas/tn/3.0/CommonTransportElements.xsd
                                      urn:x-inspire:specification:gmlas:RoadTransportNetwork:3.0 http://inspire.ec.europa.eu/schemas/tn-ro/3.0/RoadTransportNetwork.xsd
                                      urn:x-inspire:specification:gmlas:GeographicalNames:3.0 http://inspire.ec.europa.eu/schemas/gn/3.0/GeographicalNames.xsd"
                  gml:id="NL.RWS.NWB.TN_RO.{fme:get-attribute("fk_veld4")}">
        <gml:metaDataProperty about="" nilReason="other:unpopulated" xsi:nil="true">
          <gml:GenericMetaData gml:id=""></gml:GenericMetaData>
        </gml:metaDataProperty>
        <gml:description nilReason="" gml:remoteSchema="" xlink:type="simple" xlink:href="" xlink:role="none" xlink:arcrole="none" xlink:title="" xlink:show="none" xlink:actuate="none"></gml:description>
        <gml:descriptionReference owns="false" nilReason="other:unpopulated" xsi:nil="true"/>
        <gml:identifier codeSpace="http://inspire.jrc.ec.europa.eu/">urn:x-inspire:object:id:NL.RWS.NWB.TN_RO.{fme:get-attribute("fk_veld4")}</gml:identifier>
        <gml:name codeSpace=""></gml:name>
        <gml:boundedBy nilReason="other:unpopulated" xsi:nil="true"></gml:boundedBy>
        <gml:location nilReason="other:unpopulated" xsi:nil="true"></gml:location>
        <net:networkRef nilReason="other:unpopulated" xsi:nil="true"></net:networkRef>
        <net:inspireId>
          <base:Identifier>
            <base:localId>{fme:get-attribute("fk_veld4")}</base:localId>
            <base:namespace>NL.RWS.NWB.TN_RO</base:namespace>
            <base:versionId nilReason="other:unpopulated" xsi:nil="true"></base:versionId>
          </base:Identifier>
        </net:inspireId>
        <net:beginLifespanVersion nilReason="other:unpopulated" xsi:nil="true"></net:beginLifespanVersion>
        <net:endLifespanVersion nilReason="other:unpopulated" xsi:nil="true"></net:endLifespanVersion>
        <tn:validFrom nilReason="other:unpopulated" xsi:nil="true"></tn:validFrom>
        <tn:validTo nilReason="other:unpopulated" xsi:nil="true"></tn:validTo>
        <tn-ro:areaCondition nilReason="other:unpopulated" xsi:nil="true" codeSpace=""></tn-ro:areaCondition>
        <tn-ro:direction nilReason="other:unpopulated" xsi:nil="true"></tn-ro:direction>
        <tn-ro:laneExtension nilReason="other:unpopulated" xsi:nil="true"></tn-ro:laneExtension>
        <tn-ro:speedLimitMinMaxType></tn-ro:speedLimitMinMaxType>
        <tn-ro:speedLimitSource nilReason="other:unpopulated" xsi:nil="true"></tn-ro:speedLimitSource>
        <tn-ro:speedLimitValue uom="km">{fme:get-attribute("omschr")}</tn-ro:speedLimitValue>
        <tn-ro:startLane nilReason=""></tn-ro:startLane>
        <tn-ro:validityPeriod nilReason="other:unpopulated" xsi:nil="true"></tn-ro:validityPeriod>
        <tn-ro:vehicleType nilReason="other:unpopulated" xsi:nil="true"></tn-ro:vehicleType>
        <tn-ro:weatherCondition nilReason="other:unpopulated" xsi:nil="true"></tn-ro:weatherCondition>
      </tn-ro:SpeedLimit>
    RESULT_ATTRIBUTE = _result
    -> AttributeCreator
AttributeCreator
    ATTR_LIST = ft_type,61,gml_id,fme_basicstring:17%16:NL.RWS.NWB.TN_RO.@Value(fk_veld4),binary_object,@Value(_result)
    -> AttributeExpressionRemover
AttributeExpressionRemover
    ATTR_EXP = post*
    -> BinaryEncoder
BinaryEncoder
    DEST_ATTR = binary_object
    ENCODING_TYPE = HEX
    ATTR_TO_ENCODE = binary_object
    -> 2DForcer
2DForcer
    2D -> inspire_tn_blob.gml_objects (writer POSTGIS_2)
inspire_tn_blob.gml_objects (writer POSTGIS_2)
    attributes: id serial,PRIKEY, gml_id text,none, ft_type int2, binary_object bytea
Note: weggeg.rijstroken_imp
weggeg.rijstroken_imp (reader POSTGIS_1)
    attributes: gid serial,PRIKEY, omschr varchar(40), volgnrstrk varchar(3), beginwdl varchar(1), beginkm float8, eindwdl varchar(1), eindkm float8, kantcode varchar(1), wegnummer varchar(5), fk_veld4 varchar(13), izi_side varchar(1), geom_valid bool
    -> Reprojector_2
Reprojector_2
    DEST = EPSG:4258
    SOURCE = EPSG:28992
    RASTER_CELL_SIZE = Preserve Cells
    INTERPOLATION_TYPE_NAME = Nearest Neighbor
    STROKE_ARCS = Yes
    REPROJECTED -> CoordinateSwapper_3
CoordinateSwapper_3
    SWAP_TYPE = X <-> Y
    -> 3DForcer_2
3DForcer_2
    ZVALATTR = 0
    -> CoordinateConcatenator_2
CoordinateConcatenator_2
    COORD_ATTR = _coordinates
    COORD_DELIM = " "
    COORDINATES_TO_INCLUDE_DIS = X Y Z
    ELEMENT_DELIM = ,
    -> CoordinateSwapper_4
CoordinateSwapper_4
    SWAP_TYPE = X <-> Y
    -> StringReplacer_2
StringReplacer_2
    FIND_TEXT = "^2,[0123456789]*,0 "
    SRC_ATTRS = _coordinates
    REGEXP = yes
    CASE = no
