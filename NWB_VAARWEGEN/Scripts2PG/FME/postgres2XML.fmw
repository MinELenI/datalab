FME workspace postgres2XML.fmw

Parameters:
- XML_DIR = H:\Projects\PDOK\NWB_VAARWEGEN\Scripts2PG\XML_uit   # Fanout Directory
- LOG_FILE = H:\Projects\PDOK\NWB_VAARWEGEN\Scripts2PG\Log\Inspre_NWB_Hydro_XML.log   # Log File

Readers:
- POSTGRES_1: POSTGRES from pdok

Writers:
- TEXTLINE_1: TEXTLINE to H:\Projects\PDOK\Scripts2PG\XML_uit\test_5.xml

inspire_hy_blob.gml_objects (reader POSTGRES_1)
    attributes: id serial,PRIKEY, gml_id text,PRIKEY, ft_type int2, binary_object bytea, gml_bounded_by char(80),GIST
    -> BinaryDecoder
BinaryDecoder
    DEST_ATTR = _decoded
    ATTR_TO_DECODE = binary_object
    ENCODING_TYPE = HEX
    ATTR_ENCODING = utf-8
    -> AttributeCopier
AttributeCopier
    ATTR_LIST = text_line_data,_decoded
    -> text_line (writer TEXTLINE_1)
text_line (writer TEXTLINE_1)
    attributes: text_line_data buffer
