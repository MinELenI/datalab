FME workspace INSPIRE_NWB_20121116.fmw

Parameters:
- LOG_FILE = H:\temp\Inspre_NWB_Hydro.log   # Log File
- MAX_FEATURES = 2   # Max Features to Read

Readers:
- POSTGIS_1: POSTGIS from pdok

Writers:
- POSTGIS_2: POSTGIS to pdok

nwbvaarwegen.vaarwegvakken_imp (reader POSTGIS_1)
    attributes: gid serial,PRIKEY, vwk_id float8, vwk_begdtm date, vwj_id_beg float8, vwj_id_end float8, vaktype varchar(1), vrt_code varchar(6), vrt_naam varchar(240), vwg_nr int2, vwg_naam varchar(240), begkm float8, endkm float8, geom_valid bool
    -> Reprojector
Reprojector
    DEST = EPSG:4258
    SOURCE = EPSG:28992
    RASTER_CELL_SIZE = Preserve Cells
    INTERPOLATION_TYPE_NAME = Nearest Neighbor
    STROKE_ARCS = Yes
    REPROJECTED -> DateFormatter
DateFormatter
    FMT = %Y-%m-%dT00:00:00
    DATE_ATTR = vwk_begdtm
    -> CoordinateSwapper
CoordinateSwapper
    SWAP_TYPE = X <-> Y
    -> CoordinateConcatenator
CoordinateConcatenator
    COORD_ATTR = _coordinates
    COORD_DELIM = " "
    COORDINATES_TO_INCLUDE_DIS = X Y
    ELEMENT_DELIM = ,
    -> CoordinateSwapper_2
CoordinateSwapper_2
    SWAP_TYPE = X <-> Y
    -> LengthCalculator
LengthCalculator
    LEN_ATTR = _length
    DIM = 2
    MULT = 1
    -> AttributeRounder
AttributeRounder
    ROUND_TYPE = nearest
    PLACES = 0
    SRC_ATTRS = _length
    -> StringReplacer
StringReplacer
    FIND_TEXT = "^2,[0123456789]* "
    SRC_ATTRS = _coordinates
    REGEXP = yes
    CASE = no
    -> XMLTemplater_3
XMLTemplater_3
    OUTPUT_XML_HEADER = Yes
    VISIBLE_QUERY_VALIDATE = No
    ROOT_QUERY_EXPR:
      <hy-p:Watercourse xmlns:base="urn:x-inspire:specification:gmlas:BaseTypes:3.2"
                                       xmlns:gmd="http://www.isotc211.org/2005/gmd"
                                       xmlns:gml="http://www.opengis.net/gml/3.2"
                                       xmlns:gn="urn:x-inspire:specification:gmlas:GeographicalNames:3.0"
                                       xmlns:hy="urn:x-inspire:specification:gmlas:HydroBase:3.0"
                                       xmlns:hy-p="urn:x-inspire:specification:gmlas:HydroPhysicalWaters:3.0"
                                       xmlns:lc="urn:x-inspire:specification:gmlas:LandCover:0.0"
                                       xmlns:gco="http://www.isotc211.org/2005/gco"
                                       xmlns:xlink="http://www.w3.org/1999/xlink"
                                       xmlns:gsr="http://www.isotc211.org/2005/gsr"
                                       xmlns:gts="http://www.isotc211.org/2005/gts"
                                       xmlns:sr="urn:x-inspire:specification:gmlas:SeaRegions:0.0"
                                       xmlns:net="urn:x-inspire:specification:gmlas:Network:3.2"
                                       xmlns:hy-n="urn:x-inspire:specification:gmlas:HydroNetwork:3.0"
                                       xmlns:nrz="urn:x-inspire:specification:gmlas:NaturalRiskZones:0.0"
                                       xmlns:wfd="urn:x-inspire:specification:gmlas:WaterFrameworkDirective:0.0"
                                       xmlns:gss="http://www.isotc211.org/2005/gss"
                                       xmlns:xsi="http://www.w3.org/2001/XMLSchema-instance"
                                       xsi:schemaLocation="urn:x-inspire:specification:gmlas:BaseTypes:3.2 http://inspire.ec.europa.eu/schemas/base/3.2/BaseTypes.xsd
                                       urn:x-inspire:specification:gmlas:HydroPhysicalWaters:3.0 http://inspire.ec.europa.eu/schemas/hy-p/3.0/HydroPhysicalWaters.xsd
                                       urn:x-inspire:specification:gmlas:GeographicalNames:3.0 http://inspire.ec.europa.eu/schemas/gn/3.0/GeographicalNames.xsd"
                                       gml:id="{fme:get-attribute("gid")}">
        <gml:identifier codeSpace="http://inspire.jrc.ec.europa.eu/">urn:x-inspire:object:id:NL.RWS.NWB.HY-P.{fme:get-attribute("gid")}</gml:identifier>
        <hy-p:geographicalName nilReason="">
          <gn:GeographicalName>
            <gn:language>NL</gn:language>
            <gn:nativeness>endonym</gn:nativeness>
            <gn:nameStatus nilReason="other:unpopulated" xsi:nil="true"></gn:nameStatus>
            <gn:sourceOfName>Rijkswaterstaat</gn:sourceOfName>
            <gn:spelling>
              <gn:SpellingOfName>
                <gn:text>{fme:get-attribute("vwg_naam")}</gn:text>
                <gn:script>Latn</gn:script>
                <gn:transliterationScheme nilReason="other:unpopulated" xsi:nil="true"/>
              </gn:SpellingOfName>
            </gn:spelling>
            <gn:grammaticalGender nilReason="other:unpopulated" xsi:nil="true"/>
            <gn:grammaticalNumber nilReason="other:unpopulated" xsi:nil="true"/>
          </gn:GeographicalName>
        </hy-p:geographicalName>
        <hy-p:hydroId nilReason="">
          <hy:HydroIdentifier>
            <hy:classificationScheme></hy:classificationScheme>
            <hy:localId></hy:localId>
            <hy:namespace></hy:namespace>
          </hy:HydroIdentifier>
        </hy-p:hydroId>
        <hy-p:relatedHydroObject owns="false" nilReason="" gml:remoteSchema="" xlink:type="simple" xlink:href="" xlink:role="" xlink:arcrole="" xlink:title="" xlink:show="" xlink:actuate=""/>
        <hy-p:beginLifespanVersion>{fme:get-attribute("vwk_begdtm")}</hy-p:beginLifespanVersion>
        <hy-p:endLifespanVersion nilReason="other:unpopulated" xsi:nil="true"></hy-p:endLifespanVersion>
        <hy-p:geometry nilReason="" gml:remoteSchema="" xlink:type="simple" xlink:href="" xlink:role="none" xlink:arcrole="none" xlink:title="" xlink:show="none" xlink:actuate="none" owns="false">
          <gml:LineString srsName="urn:ogc:def:crs:EPSG::4258" srsDimension="2" gml:id="NL.RWS.NWB.HY-P.{fme:get-attribute("gid")}_L">
            <gml:coordinates>{fme:get-attribute("_coordinates")}</gml:coordinates>
          </gml:LineString>
        </hy-p:geometry>
        <hy-p:inspireId>
          <base:Identifier>
            <base:localId>{fme:get-attribute("gid")}</base:localId>
            <base:namespace>NL.RWS.NWB.HY-P</base:namespace>
            <base:versionId nilReason="other:unpopulated" xsi:nil="true"></base:versionId>
          </base:Identifier>
        </hy-p:inspireId>
        <hy-p:levelOfDetail owns="false">
          <gmd:MD_Resolution></gmd:MD_Resolution>
        </hy-p:levelOfDetail>
        <hy-p:localType gco:nilReason="" uuidref="" xlink:type="simple" xlink:href="" xlink:role="" xlink:arcrole="" xlink:title="" xlink:show="" xlink:actuate="">
          <gmd:LocalisedCharacterString id="" locale=""></gmd:LocalisedCharacterString>
        </hy-p:localType>
        <hy-p:origin nilReason="other:unpopulated" xsi:nil="true"></hy-p:origin>
        <hy-p:persistence nilReason="other:unpopulated" xsi:nil="true"></hy-p:persistence>
        <hy-p:tidal nilReason="other:unpopulated" xsi:nil="true"></hy-p:tidal>
        <hy-p:bank owns="false" nilReason="" gml:remoteSchema="" xlink:type="simple" xlink:href="" xlink:role="" xlink:arcrole="" xlink:title="" xlink:show="" xlink:actuate=""/>
        <hy-p:drainsBasin owns="false" nilReason="" gml:remoteSchema="" xlink:type="simple" xlink:href="" xlink:role="" xlink:arcrole="" xlink:title="" xlink:show="" xlink:actuate=""/>
        <hy-p:neighbour owns="false" nilReason="" gml:remoteSchema="" xlink:type="simple" xlink:href="" xlink:role="" xlink:arcrole="" xlink:title="" xlink:show="" xlink:actuate=""/>
        <hy-p:condition nilReason="other:unpopulated" xsi:nil="true"></hy-p:condition>
        <hy-p:delineationKnown nilReason=""></hy-p:delineationKnown>
        <hy-p:length nilReason="" uom="METER">{fme:get-attribute("_length")}</hy-p:length>
        <hy-p:level nilReason="other:unpopulated" xsi:nil="true"></hy-p:level>
        <hy-p:streamOrder nilReason="other:unpopulated" xsi:nil="true"></hy-p:streamOrder>
        <hy-p:width nilReason="other:unpopulated" xsi:nil="true"></hy-p:width>
      </hy-p:Watercourse>
    RESULT_ATTRIBUTE = _result
    -> AttributeCreator_2
AttributeCreator_2
    ATTR_LIST = ft_type,99,gml_id,fme_basicstring:16%11:NL.RWS.NWB.HY-P.@Value(gid),binary_object,@Value(_result)
    -> AttributeExpressionRemover
AttributeExpressionRemover
    ATTR_EXP = post*
    -> BinaryEncoder
BinaryEncoder
    DEST_ATTR = binary_object
    ENCODING_TYPE = HEX
    ATTR_TO_ENCODE = binary_object
    -> inspire_hy_blob.gml_objects (writer POSTGIS_2)
inspire_hy_blob.gml_objects (writer POSTGIS_2)
    attributes: id serial,PRIKEY, gml_id text,none, ft_type int2, binary_object bytea
