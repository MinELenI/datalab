FME workspace INSPIRE_NWB.fmw

Parameters:
- LOG_FILE = $(FME_MF_DIR)Inspre_NWB_Hydro.log   # Log File
- MAX_FEATURES = 10   # Max Features to Read
- DestDataset_INSPIRE = $(FME_MF_DIR)Vaarwegen.xml   # Destination Geography Markup Language (GML) File

Readers:
- POSTGIS_1: POSTGIS from pdok

Writers:
- INSPIRE_1: INSPIRE to $(DestDataset_INSPIRE)

nwbvaarwegen.vaarwegvakken_imp (reader POSTGIS_1)
    attributes: gid serial,PRIKEY, vwk_id float8, vwk_begdtm date, vwj_id_beg float8, vwj_id_end float8, vaktype varchar(1), vrt_code varchar(6), vrt_naam varchar(240), vwg_nr int2, vwg_naam varchar(240), begkm float8, endkm float8, geom_valid bool
    -> LengthCalculator
LengthCalculator
    LEN_ATTR = _length
    MULT = 1
    DIM = 2
    -> AttributeRounder
AttributeRounder
    SRC_ATTRS = _length
    ROUND_TYPE = nearest
    PLACES = 0
    -> CsmapReprojector
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> DateFormatter
DateFormatter
    DATE_ATTR = vwk_begdtm
    FMT = %Y-%m-%dT00:00:00
    -> AttributeCreator_2
AttributeCreator_2
    ATTR_LIST = gml_id,@Value(gid),gml_identifier,@Value(gid),gml_metaDataProperty{0}.nilReason,other:unpopulated,geographicalName{0}.GeographicalName.language,NL,geographicalName{0}.GeographicalName.nativeness,endonym,geographicalName{0}.GeographicalName.nameStatus.nilReason,other:unpopulated,geographicalName{0}.GeographicalName.sourceOfName,Rijkstwaterstaat,geographicalName{0}.GeographicalName.pronunciation.nilReason,other:unpopulated,geographicalName{0}.GeographicalName.spelling{0}.SpellingOfName.text,@Value(vwg_naam),geographicalName{0}.GeographicalName.spelling{0}.SpellingOfName.script,Latn,geographicalName{0}.GeographicalName.grammaticalGender.nilReason,other:unpopulated,geographicalName{0}.GeographicalName.grammaticalNumber.nilReason,other:unpopulated,beginLifespanVersion,@Value(vwk_begdtm),endLifespanVersion.nilReason,other:unpopulated,inspireId.Identifier.localId,@Value(gid),inspireId.Identifier.namespace,NL.RWS.NWB.HY-P,inspireId.Identifier.versionId,@Value(vwk_begdtm),length,@Value(_length),length.uom,METER,level.nilReason,other:unpopulated,streamOrder.nilReason,other:unpopulated,width.nilReason,other:unpopulated
    -> GeometryPropertySetter
GeometryPropertySetter
    OVERWRITE_CHOICE = Yes
    SETTYPE_PARAM = Geometry Name
    GEOM_NAME_FIELD = geometry
    SET -> Watercourse (writer INSPIRE_1)
Watercourse (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, geographicalName{}.nilReason xml_buffer, geographicalName{}.xsi_nil xml_boolean, geographicalName{}.GeographicalName.language xml_buffer, geographicalName{}.GeographicalName.language.nilReason xml_buffer, geographicalName{}.GeographicalName.language.xsi_nil xml_boolean, geographicalName{}.GeographicalName.nativeness xml_buffer, geographicalName{}.GeographicalName.nativeness.nilReason xml_buffer, geographicalName{}.GeographicalName.nativeness.codeSpace xml_buffer, geographicalName{}.GeographicalName.nativeness.xsi_nil xml_boolean,
      geographicalName{}.GeographicalName.nameStatus xml_buffer, geographicalName{}.GeographicalName.nameStatus.nilReason xml_buffer, geographicalName{}.GeographicalName.nameStatus.codeSpace xml_buffer, geographicalName{}.GeographicalName.nameStatus.xsi_nil xml_boolean, geographicalName{}.GeographicalName.sourceOfName xml_buffer, geographicalName{}.GeographicalName.sourceOfName.nilReason xml_buffer, geographicalName{}.GeographicalName.sourceOfName.xsi_nil xml_boolean, geographicalName{}.GeographicalName.pronunciation.nilReason xml_buffer, geographicalName{}.GeographicalName.pronunciation.xsi_nil xml_boolean, geographicalName{}.GeographicalName.pronunciation.PronunciationOfName.pronunciationSoundLink xml_buffer, geographicalName{}.GeographicalName.pronunciation.PronunciationOfName.pronunciationSoundLink.nilReason xml_buffer, geographicalName{}.GeographicalName.pronunciation.PronunciationOfName.pronunciationSoundLink.xsi_nil xml_boolean, geographicalName{}.GeographicalName.pronunciation.PronunciationOfName.pronunciationIPA xml_buffer, geographicalName{}.GeographicalName.pronunciation.PronunciationOfName.pronunciationIPA.nilReason xml_buffer, geographicalName{}.GeographicalName.pronunciation.PronunciationOfName.pronunciationIPA.xsi_nil xml_boolean, geographicalName{}.GeographicalName.spelling{}.SpellingOfName.text xml_buffer, geographicalName{}.GeographicalName.spelling{}.SpellingOfName.script xml_buffer, geographicalName{}.GeographicalName.spelling{}.SpellingOfName.script.nilReason xml_buffer, geographicalName{}.GeographicalName.spelling{}.SpellingOfName.script.xsi_nil xml_boolean, geographicalName{}.GeographicalName.spelling{}.SpellingOfName.transliterationScheme xml_buffer, geographicalName{}.GeographicalName.spelling{}.SpellingOfName.transliterationScheme.nilReason xml_buffer, geographicalName{}.GeographicalName.spelling{}.SpellingOfName.transliterationScheme.xsi_nil xml_boolean, geographicalName{}.GeographicalName.grammaticalGender xml_buffer, geographicalName{}.GeographicalName.grammaticalGender.nilReason xml_buffer, geographicalName{}.GeographicalName.grammaticalGender.codeSpace xml_buffer, geographicalName{}.GeographicalName.grammaticalGender.xsi_nil xml_boolean, geographicalName{}.GeographicalName.grammaticalNumber xml_buffer, geographicalName{}.GeographicalName.grammaticalNumber.nilReason xml_buffer, geographicalName{}.GeographicalName.grammaticalNumber.codeSpace xml_buffer, geographicalName{}.GeographicalName.grammaticalNumber.xsi_nil xml_boolean,
      hydroId{}.nilReason xml_buffer, hydroId{}.xsi_nil xml_boolean, hydroId{}.HydroIdentifier.classificationScheme xml_buffer, hydroId{}.HydroIdentifier.localId xml_buffer, hydroId{}.HydroIdentifier.namespace xml_buffer, relatedHydroObject{}.owns xml_boolean, relatedHydroObject{}.nilReason xml_buffer, relatedHydroObject{}.gml_remoteSchema xml_buffer, relatedHydroObject{}.xlink_href xml_buffer, beginLifespanVersion xml_datetime, beginLifespanVersion.nilReason xml_buffer, beginLifespanVersion.xsi_nil xml_boolean, endLifespanVersion xml_datetime, endLifespanVersion.nilReason xml_buffer, endLifespanVersion.xsi_nil xml_boolean, geometry xml_geometry, inspireId.Identifier.localId xml_buffer, inspireId.Identifier.namespace xml_buffer, inspireId.Identifier.versionId xml_buffer, inspireId.Identifier.versionId.nilReason xml_buffer, inspireId.Identifier.versionId.xsi_nil xml_boolean, levelOfDetail.owns xml_boolean, levelOfDetail.MD_Resolution.equivalentScale.nilReason xml_buffer, levelOfDetail.MD_Resolution.equivalentScale.uuidref xml_buffer, levelOfDetail.MD_Resolution.equivalentScale.xlink_href xml_buffer, levelOfDetail.MD_Resolution.equivalentScale.MD_RepresentativeFraction.id xml_buffer, levelOfDetail.MD_Resolution.equivalentScale.MD_RepresentativeFraction.uuid xml_buffer, levelOfDetail.MD_Resolution.equivalentScale.MD_RepresentativeFraction.denominator.gco_nilReason xml_buffer, levelOfDetail.MD_Resolution.equivalentScale.MD_RepresentativeFraction.denominator.Integer xml_int64, levelOfDetail.MD_Resolution.distance.gco_nilReason xml_buffer,
      levelOfDetail.MD_Resolution.distance.Distance xml_real64, levelOfDetail.MD_Resolution.distance.Distance.uom xml_buffer, localType.gco_nilReason xml_buffer, localType.uuidref xml_buffer, localType.xlink_href xml_buffer, localType.xsi_nil xml_boolean, localType.LocalisedCharacterString xml_buffer, localType.LocalisedCharacterString.id xml_buffer, localType.LocalisedCharacterString.locale xml_buffer, origin xml_char(7), origin.nilReason xml_buffer, origin.xsi_nil xml_boolean, persistence xml_buffer, persistence.nilReason xml_buffer, persistence.codeSpace xml_buffer, persistence.xsi_nil xml_boolean, tidal xml_boolean, tidal.nilReason xml_buffer, tidal.xsi_nil xml_boolean, bank{}.owns xml_boolean, bank{}.nilReason xml_buffer, bank{}.gml_remoteSchema xml_buffer, bank{}.xlink_href xml_buffer, bank{}.xsi_nil xml_boolean, drainsBasin{}.owns xml_boolean, drainsBasin{}.nilReason xml_buffer, drainsBasin{}.gml_remoteSchema xml_buffer, drainsBasin{}.xlink_href xml_buffer, drainsBasin{}.xsi_nil xml_boolean, neighbour{}.owns xml_boolean,
      neighbour{}.nilReason xml_buffer, neighbour{}.gml_remoteSchema xml_buffer, neighbour{}.xlink_href xml_buffer, neighbour{}.xsi_nil xml_boolean, condition xml_buffer, condition.nilReason xml_buffer, condition.codeSpace xml_buffer, condition.xsi_nil xml_boolean, delineationKnown xml_boolean, delineationKnown.nilReason xml_buffer, delineationKnown.xsi_nil xml_boolean, length xml_real64, length.nilReason xml_buffer, length.uom xml_buffer, length.xsi_nil xml_boolean, level xml_char(19), level.nilReason xml_buffer, level.xsi_nil xml_boolean, streamOrder.nilReason xml_buffer, streamOrder.xsi_nil xml_boolean, streamOrder.HydroOrderCode.order xml_buffer, streamOrder.HydroOrderCode.orderScheme xml_buffer, streamOrder.HydroOrderCode.scope xml_buffer, width.nilReason xml_buffer, width.xsi_nil xml_boolean, width.WidthRange.lower xml_real64, width.WidthRange.lower.uom xml_buffer, width.WidthRange.upper xml_real64, width.WidthRange.upper.uom xml_buffer
