FME workspace BRK_INSPIRE_CP_20131206.fmw

Parameters:
- LOG_FILE = $(FME_MF_DIR)test.log   # Log File
- MAX_FEATURES =   # Max Features to Read

Readers:
- POSTGIS_1: POSTGIS from pdok

Writers:
- POSTGIS_2: POSTGIS to pdok

Note: Lezen tabel brk.perceel_imp
brk.perceel_imp (reader POSTGIS_1)
    attributes: gid int4,PRIKEY, perceelnr varchar(17), geom_valid bool
    -> AttributeKeeper_2
AttributeKeeper_2
    KEEP_ATTRS = gid,perceelnr,fme_geometry
    -> SubstringExtractor
SubstringExtractor
    RESULT_ATTR = kadgem
    SRC_ATTR = perceelnr
    START = 0
    END = 4
    -> SubstringExtractor_2
SubstringExtractor_2
    RESULT_ATTR = sectie
    SRC_ATTR = perceelnr
    START = 5
    END = 6
    -> SubstringExtractor_3
SubstringExtractor_3
    RESULT_ATTR = percnr
    SRC_ATTR = perceelnr
    START = 7
    END = 11
    -> AttributeTrimmer
AttributeTrimmer
    SRC_ATTRS = kadgem,sectie,percnr
    TRIM_TO_NONE = Yes
    TRIM_TYPE = Both
    -> AttributeCreator
AttributeCreator
    ATTR_LIST = kadgem_sectie_pnr,@Value(kadgem).@Value(sectie).@Value(percnr),NameSpace,NL.KAD.CP
    -> AreaCalculator
Note: Berekenen oppervlak en afronden op gehele meters
AreaCalculator
    AREA_ATTR = _area
    AREA_TYPE = Plane Area
    MULT = 1
    -> AttributeRounder
AttributeRounder
    SRC_ATTRS = _area
    ROUND_TYPE = nearest
    PLACES = 0
    -> CsmapReprojector
Note: Reprojectie naar EPSG:4258
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> GeometryExtractor
GeometryExtractor
    ATTR = _geometry
    OMIT_NAMESPACES_DISPLAY = Yes
    KIND_LONG = GML v3.2.1
    -> XMLTemplater_8
XMLTemplater_8
    RESULT_ATTRIBUTE = binary_object
    ROOT_QUERY_EXPR:
          <cp:CadastralParcel xmlns:gts="http://www.isotc211.org/2005/gts" xmlns:cp="urn:x-inspire:specification:gmlas:CadastralParcels:3.0" xmlns:gco="http://www.isotc211.org/2005/gco" xmlns:gsr="http://www.isotc211.org/2005/gsr" xmlns:au="urn:x-inspire:specification:gmlas:AdministrativeUnits:3.0" xmlns:stat="urn:x-inspire:specification:gmlas:StatisticalUnits:0.0" xmlns:base="urn:x-inspire:specification:gmlas:BaseTypes:3.2" xmlns:gml="http://www.opengis.net/gml/3.2" xmlns:xlink="http://www.w3.org/1999/xlink" xmlns:xsi="http://www.w3.org/2001/XMLSchema-instance" xmlns:gss="http://www.isotc211.org/2005/gss" xmlns:gmd="http://www.isotc211.org/2005/gmd" xmlns:gn="urn:x-inspire:specification:gmlas:GeographicalNames:3.0"  gml:id="NL.KAD.CP.{fme:get-attribute("kadgem_sectie_pnr")}">
            <gml:identifier codeSpace="http://inspire.jrc.ec.europa.eu/">urn:x-inspire:object:id:{fme:get-attribute("NameSpace")}.{fme:get-attribute("kadgem_sectie_pnr")}</gml:identifier>
            <cp:areaValue uom="m2">{fme:get-attribute("_area")}</cp:areaValue>
            <cp:beginLifespanVersion xsi:nil="true" nilReason="other:unpopulated"/>
            <cp:endLifespanVersion xsi:nil="true" nilReason="other:unpopulated"/>
            <cp:geometry>{fme:get-attribute("_geometry")}</cp:geometry>
            <cp:inspireId>
              <base:Identifier>
                <base:localId>{fme:get-attribute("kadgem_sectie_pnr")}</base:localId>
                <base:namespace>{fme:get-attribute("NameSpace")}</base:namespace>
              </base:Identifier>
            </cp:inspireId>
            <cp:label>{fme:get-attribute("percnr")}</cp:label>
            <cp:nationalCadastralReference>{fme:get-attribute("kadgem_sectie_pnr")}</cp:nationalCadastralReference>
            <cp:referencePoint xsi:nil="true" nilReason="other:unpopulated"></cp:referencePoint>
          </cp:CadastralParcel>
    VISIBLE_QUERY_VALIDATE = No
    OUTPUT_XML_HEADER = No
    -> AttributeCreator_3
Note: ft=52 voor kadastrale percelen
AttributeCreator_3
    ATTR_LIST = ft_type,52
    -> StringConcatenator_3
Note: Maken gml_id
StringConcatenator_3
    PARM_LINE = @Value(NameSpace).CadastrelParcel.@Value(kadgem_sectie_pnr)
    VAL_ATTR = gml_id
    -> BoundingBoxReplacer
Note: Maken bounding box geometrie
BoundingBoxReplacer
    BOXTYPE = Bounding Box
    BOX -> AttributeExpressionRemover_3
Note: Verwijderen alle originele / postgres attributen
AttributeExpressionRemover_3
    ATTR_EXP = postgis*
    -> inspire_cp.gml_objects (writer POSTGIS_2)
inspire_cp.gml_objects (writer POSTGIS_2)
    attributes: id serial,PRIKEY, gml_id text,none, ft_type int2, binary_object bytea
