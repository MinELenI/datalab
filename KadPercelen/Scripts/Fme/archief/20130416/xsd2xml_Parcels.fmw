FME workspace xsd2xml_Parcels.fmw

Parameters:
- DestDataset_TEXTLINE = D:\Projects\PDOK\KadPercelen\Scripts\XSD\Parcels.xml   # Destination Text File File

Writers:
- TEXTLINE_1: TEXTLINE to $(DestDataset_TEXTLINE)

Creator
    NUM = 1
    GEOMTYPE = Geometry Object
    CREATED -> KP_XMLSampleGenerator
KP_XMLSampleGenerator: XMLSampleGenerator
    PATH_TO_ELEMENT = cp:CadastralParcel
    RESULT_ATTRIBUTE = _result
    GENERATE_OPTIONAL_ATTRIBUTES = Yes
    GENERATE_COMMENTS = No
    CHOICE_OPTIONS = Generate no options
    GENERATE_HEADER = No
    SCHEMA_LOCATION = D:\Projects\PDOK\KadPercelen\Scripts\XSD\CadastralParcels.xsd
    GENERATE_OPTIONAL_ELEMENTS = Yes
    SUBSTITUTION_GROUP_OPTIONS = Generate first member only
    -> text_line (writer TEXTLINE_1)
text_line (writer TEXTLINE_1)
    attributes: text_line_data buffer
