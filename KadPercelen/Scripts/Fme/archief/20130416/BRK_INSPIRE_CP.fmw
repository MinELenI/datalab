FME workspace BRK_INSPIRE_CP.fmw

Parameters:
- LOG_FILE = $(FME_MF_DIR)test.log   # Log File
- MAX_FEATURES =   # Max Features to Read

Readers:
- POSTGIS_1: POSTGIS from pdok

Writers:
- POSTGIS_2: POSTGIS to pdok

Note: Lezen tabel brk.perceel_imp
brk.perceel_imp (reader POSTGIS_1)
    attributes: gid int4,PRIKEY, perceelnr varchar(17), geom_valid bool
    -> AttributeKeeper_2
AttributeKeeper_2
    KEEP_ATTRS = gid,perceelnr
    -> DuplicateRemover_3
Note: Verwijderen dubbele percelen
DuplicateRemover_3
    KEYATTR = perceelnr
    UNIQUE -> AttributeCopier
AttributeCopier
    ATTR_LIST = kadgem_sectie_pnr,perceelnr
    -> StringReplacer_2
Note: Verwijderen G0000 en spaties uit perceelnummer
StringReplacer_2
    SRC_ATTRS = kadgem_sectie_pnr
    REGEXP = no
    CASE = no
    FIND_TEXT = G0000
    -> StringReplacer_3
StringReplacer_3
    SRC_ATTRS = kadgem_sectie_pnr
    REGEXP = yes
    CASE = no
    REPLACE_TEXT = .
    FIND_TEXT = " +"
    -> AreaCalculator
Note: Berekenen oppervlak en afronden op gehele meters
AreaCalculator
    AREA_ATTR = _area
    AREA_TYPE = Plane Area
    MULT = 1
    -> AttributeRounder
AttributeRounder
    SRC_ATTRS = _area
    ROUND_TYPE = nearest
    PLACES = 0
    -> CsmapReprojector
Note: Reprojectie naar EPSG:4258
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> CoordinateSwapper
Note: Omkeren volgorde lat en lon voor GML
CoordinateSwapper
    SWAP_TYPE = X <-> Y
    -> DonutHoleExtractor
DonutHoleExtractor
    OUTERSHELL -> Orientor
    HOLE -> Orientor_2
Orientor
    KIND = LEFT_HAND_RULE
    ORIENTED -> CoordinateConcatenator
CoordinateConcatenator
    COORD_ATTR = exterior
    COORD_DELIM = " "
    COORDINATES_TO_INCLUDE_DIS = X Y
    ELEMENT_DELIM = " "
    -> FeatureMerger [input 1]
Orientor_2
    KIND = RIGHT_HAND_RULE
    ORIENTED -> CoordinateConcatenator_2
CoordinateConcatenator_2
    COORD_ATTR = interior
    COORD_DELIM = " "
    COORDINATES_TO_INCLUDE_DIS = X Y
    ELEMENT_DELIM = " "
    -> AttributeKeeper
AttributeKeeper
    KEEP_ATTRS = perceelnr,interior
    -> FeatureMerger [input 2]
FeatureMerger
    BUILD_INCOMPLETE = Yes
    PROCESS_DUPS = No
    MERGE_TYPE = Attributes Only
    REFERATTR = perceelnr
    REFEEATTR = perceelnr
    COMPLETE -> XMLTemplater_8
    INCOMPLETE -> XMLTemplater_2
XMLTemplater_8
    RESULT_ATTRIBUTE = binary_object
    ROOT_QUERY_EXPR:
          <CP:CadastralParcel xmlns:base="urn:x-inspire:specification:gmlas:BaseTypes:3.2" xmlns:CP="urn:x-inspire:specification:gmlas:CadastralParcels:3.0" xmlns:gmd="http://www.isotc211.org/2005/gmd" xmlns:xlink="http://www.w3.org/1999/xlink" xmlns:xsi="http://www.w3.org/2001/XMLSchema-instance" xmlns:gml="http://www.opengis.net/gml/3.2" xmlns:gml2="http://www.opengis.net/gml" xmlns:ogr="http://ogr.maptools.org/" xmlns:wfs="http://www.opengis.net/wfs" xsi:schemaLocation="urn:x-inspire:specification:gmlas:BaseTypes:3.2 http://schemas.kademo.nl/inspire/v3.0.1/BaseTypes.xsd urn:x-inspire:specification:gmlas:CadastralParcels:3.0 http://schemas.kademo.nl/inspire/v3.0.1/CadastralParcels.xsd"  gml:id="NL.KAD.CP.{fme:get-attribute("kadgem_sectie_pnr")}">
            <gml:identifier codeSpace="http://inspire.jrc.ec.europa.eu/">urn:x-inspire:object:id:NL.KAD.CP.{fme:get-attribute("kadgem_sectie_pnr")}</gml:identifier>
            <CP:areaValue uom="m2">{fme:get-attribute("_area")}</CP:areaValue>
            <CP:beginLifespanVersion xsi:nil="true" nilReason="other:unpopulated"/>
            <CP:endLifespanVersion xsi:nil="true" nilReason="other:unpopulated"/>
            <CP:geometry>
              <gml:MultiSurface gml:id="MultiSurface_NL.KAD.CP.{fme:get-attribute("kadgem_sectie_pnr")}" srsName="urn:ogc:def:crs:EPSG::4258">
                <gml:surfaceMember>
                  <gml:Surface gml:id="Surface_NL.KAD.CP.{fme:get-attribute("kadgem_sectie_pnr")}.1" srsName="urn:ogc:def:crs:EPSG::4258">
                    <gml:patches>
                      <gml:PolygonPatch interpolation="planar">
                        <gml:exterior>
                          <gml:LinearRing>
                            <gml:posList srsName="urn:ogc:def:crs:EPSG::4258" srsDimension="2">{fme:get-attribute("exterior")}</gml:posList>
                          </gml:LinearRing>
                        </gml:exterior>
                        <gml:interior>
                          <gml:LinearRing>
                            <gml:posList srsName="urn:ogc:def:crs:EPSG::4258" srsDimension="2">{fme:get-attribute("interior")}</gml:posList>
                          </gml:LinearRing>
                        </gml:interior>
                      </gml:PolygonPatch>
                    </gml:patches>
                  </gml:Surface>
                </gml:surfaceMember>
              </gml:MultiSurface>
            </CP:geometry>
            <CP:inspireId>
              <base:Identifier>
                <base:localId>{fme:get-attribute("kadgem_sectie_pnr")}</base:localId>
                <base:namespace>NL.KAD.CP</base:namespace>
              </base:Identifier>
            </CP:inspireId>
            <CP:label>{fme:get-attribute("kadgem_sectie_pnr")}</CP:label>
            <CP:nationalCadastralReference>{fme:get-attribute("kadgem_sectie_pnr")}</CP:nationalCadastralReference>
          </CP:CadastralParcel>
    VISIBLE_QUERY_VALIDATE = No
    OUTPUT_XML_HEADER = No
    -> AttributeCreator_3
XMLTemplater_2
    RESULT_ATTRIBUTE = binary_object
    ROOT_QUERY_EXPR:
          <CP:CadastralParcel xmlns:base="urn:x-inspire:specification:gmlas:BaseTypes:3.2" xmlns:CP="urn:x-inspire:specification:gmlas:CadastralParcels:3.0" xmlns:gmd="http://www.isotc211.org/2005/gmd" xmlns:xlink="http://www.w3.org/1999/xlink" xmlns:xsi="http://www.w3.org/2001/XMLSchema-instance" xmlns:gml="http://www.opengis.net/gml/3.2" xmlns:gml2="http://www.opengis.net/gml" xmlns:ogr="http://ogr.maptools.org/" xmlns:wfs="http://www.opengis.net/wfs" xsi:schemaLocation="urn:x-inspire:specification:gmlas:BaseTypes:3.2 http://schemas.kademo.nl/inspire/v3.0.1/BaseTypes.xsd urn:x-inspire:specification:gmlas:CadastralParcels:3.0 http://schemas.kademo.nl/inspire/v3.0.1/CadastralParcels.xsd"  gml:id="NL.KAD.CP.{fme:get-attribute("kadgem_sectie_pnr")}">
            <gml:identifier codeSpace="http://inspire.jrc.ec.europa.eu/">urn:x-inspire:object:id:NL.KAD.CP.{fme:get-attribute("kadgem_sectie_pnr")}</gml:identifier>
            <CP:areaValue uom="m2">{fme:get-attribute("_area")}</CP:areaValue>
            <CP:beginLifespanVersion xsi:nil="true" nilReason="other:unpopulated"/>
            <CP:endLifespanVersion xsi:nil="true" nilReason="other:unpopulated"/>
            <CP:geometry>
              <gml:MultiSurface gml:id="MultiSurface_NL.KAD.CP.{fme:get-attribute("kadgem_sectie_pnr")}" srsName="urn:ogc:def:crs:EPSG::4258">
                <gml:surfaceMember>
                  <gml:Surface gml:id="Surface_NL.KAD.CP.{fme:get-attribute("kadgem_sectie_pnr")}.1" srsName="urn:ogc:def:crs:EPSG::4258">
                    <gml:patches>
                      <gml:PolygonPatch interpolation="planar">
                        <gml:exterior>
                          <gml:LinearRing>
                            <gml:posList srsName="urn:ogc:def:crs:EPSG::4258" srsDimension="2">{fme:get-attribute("exterior")}</gml:posList>
                          </gml:LinearRing>
                        </gml:exterior>
                      </gml:PolygonPatch>
                    </gml:patches>
                  </gml:Surface>
                </gml:surfaceMember>
              </gml:MultiSurface>
            </CP:geometry>
            <CP:inspireId>
              <base:Identifier>
                <base:localId>{fme:get-attribute("kadgem_sectie_pnr")}</base:localId>
                <base:namespace>NL.KAD.CP</base:namespace>
              </base:Identifier>
            </CP:inspireId>
            <CP:label>{fme:get-attribute("kadgem_sectie_pnr")}</CP:label>
            <CP:nationalCadastralReference>{fme:get-attribute("kadgem_sectie_pnr")}</CP:nationalCadastralReference>
          </CP:CadastralParcel>
    VISIBLE_QUERY_VALIDATE = No
    OUTPUT_XML_HEADER = No
    -> AttributeCreator_3
Note: ft=52 voor kadastrale percelen
AttributeCreator_3
    ATTR_LIST = ft_type,52
    -> StringConcatenator_3
Note: Maken gml_id
StringConcatenator_3
    PARM_LINE = NL.KAD.BRK.CP.CadastrelParcel.@Value(kadgem_sectie_pnr)
    VAL_ATTR = gml_id
    -> StringReplacer
Note: Maken binary_object voor postgres database
StringReplacer
    SRC_ATTRS = binary_object
    REGEXP = no
    CASE = no
    REPLACE_TEXT = " "
    FIND_TEXT = xmlns:base="urn:x-inspire:specification:gmlas:BaseTypes:3.2" xmlns:CP="urn:x-inspire:specification:gmlas:CadastralParcels:3.0" xmlns:gmd="http://www.isotc211.org/2005/gmd" xmlns:xlink="http://www.w3.org/1999/xlink" xmlns:xsi="http://www.w3.org/2001/XMLSchema-instance" xmlns:gml="http://www.opengis.net/gml/3.2" xmlns:gml2="http://www.opengis.net/gml" xmlns:ogr="http://ogr.maptools.org/" xmlns:wfs="http://www.opengis.net/wfs" xsi:schemaLocation="urn:x-inspire:specification:gmlas:BaseTypes:3.2 http://schemas.kademo.nl/inspire/v3.0.1/BaseTypes.xsd urn:x-inspire:specification:gmlas:CadastralParcels:3.0 http://schemas.kademo.nl/inspire/v3.0.1/CadastralParcels.xsd"
    -> BinaryEncoder
BinaryEncoder
    ENCODING_TYPE = HEX
    ATTR_TO_ENCODE = binary_object
    DEST_ATTR = binary_object
    -> BoundingBoxReplacer
Note: Maken bounding box geometrie
BoundingBoxReplacer
    BOXTYPE = Bounding Box
    BOX -> AttributeExpressionRemover_3
Note: Verwijderen alle originele / postgres attributen
AttributeExpressionRemover_3
    ATTR_EXP = postgis*
    -> inspire_cp.gml_objects (writer POSTGIS_2)
inspire_cp.gml_objects (writer POSTGIS_2)
    attributes: id serial,PRIKEY, gml_id text,none, ft_type int2, binary_object bytea
