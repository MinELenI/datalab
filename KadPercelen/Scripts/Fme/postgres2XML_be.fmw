FME workspace postgres2XML_be.fmw

Parameters:
- XML_DIR = H:\Projects\PDOK\BAG\Scripts2PG\XML_uit   # Fanout Directory
- LOG_FILE = H:\Projects\PDOK\BAG\Scripts2PG\Log\BAG_postgres2XML_TFN_5.log   # Log File
- AANTAL = 5   # Number Of Records To Fetch At A Time
- TYPE = 16   # Feature type

Readers:
- POSTGRES_1: POSTGRES from pdok

Writers:
- TEXTLINE_1: TEXTLINE to H:\Projects\PDOK\Scripts2PG\XML_uit\test_5.xml

inspire_cp.gml_objects (reader POSTGRES_1)
    attributes: id serial,PRIKEY, gml_id text,PRIKEY, ft_type int2, binary_object bytea, gml_bounded_by char(80),GIST
    -> BinaryDecoder
BinaryDecoder
    ATTR_ENCODING = utf-8
    ATTR_TO_DECODE = binary_object
    ENCODING_TYPE = HEX
    DEST_ATTR = binary_object
    -> StringReplacer
StringReplacer
    SRC_ATTRS = binary_object
    REGEXP = no
    CASE = no
    REPLACE_TEXT = <
    FIND_TEXT = &lt;
    -> StringReplacer_2
StringReplacer_2
    SRC_ATTRS = binary_object
    REGEXP = no
    CASE = no
    REPLACE_TEXT = >
    FIND_TEXT = &gt;
    -> StringConcatenator
StringConcatenator
    PARM_LINE:
      <?xml version="1.0" encoding="UTF-8"?>
      <base:SpatialDataSet xmlns:gts="http://www.isotc211.org/2005/gts" xmlns:cp="urn:x-inspire:specification:gmlas:CadastralParcels:3.0" xmlns:gco="http://www.isotc211.org/2005/gco" xmlns:gsr="http://www.isotc211.org/2005/gsr" xmlns:au="urn:x-inspire:specification:gmlas:AdministrativeUnits:3.0" xmlns:stat="urn:x-inspire:specification:gmlas:StatisticalUnits:0.0" xmlns:base="urn:x-inspire:specification:gmlas:BaseTypes:3.2" xmlns:gml="http://www.opengis.net/gml/3.2" xmlns:xlink="http://www.w3.org/1999/xlink" xmlns:xsi="http://www.w3.org/2001/XMLSchema-instance" xmlns:gss="http://www.isotc211.org/2005/gss" xmlns:gmd="http://www.isotc211.org/2005/gmd" xmlns:gn="urn:x-inspire:specification:gmlas:GeographicalNames:3.0" gml:id="NL.KAD.CP">
        <base:identifier>
          <base:Identifier>
            <base:localId>0</base:localId>
            <base:namespace>NL.KAD.CP</base:namespace>
          </base:Identifier>
        </base:identifier>
        <base:metadata xsi:nil="true"/>
        <base:member>
      @Value(binary_object)
      </base:member>
      </base:SpatialDataSet>
    VAL_ATTR = text_line_data
    -> text_line (writer TEXTLINE_1)
text_line (writer TEXTLINE_1)
    attributes: text_line_data buffer
