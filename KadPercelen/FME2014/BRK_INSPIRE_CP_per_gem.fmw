FME workspace BRK_INSPIRE_CP_per_gem.fmw

Parameters:
- LOG_FILE = $(FME_MF_DIR)test.log   # Log File
- KADGEM = HGV   # Kadastrale gemeente

Readers:
- POSTGIS_1: POSTGIS from pdok

Writers:
- INSPIRE_1: INSPIRE to $(FME_MF_DIR)NKK01.xml

AttributeKeeper_2
    KEEP_ATTRS = gid,perceelnr,fme_geometry
    -> SubstringExtractor
SubstringExtractor
    RESULT_ATTR = kadgem
    SRC_ATTR = perceelnr
    START = 0
    END = 4
    -> SubstringExtractor_2
SubstringExtractor_2
    RESULT_ATTR = sectie
    SRC_ATTR = perceelnr
    START = 5
    END = 6
    -> SubstringExtractor_3
SubstringExtractor_3
    RESULT_ATTR = percnr
    SRC_ATTR = perceelnr
    START = 7
    END = 11
    -> AttributeTrimmer
AttributeTrimmer
    SRC_ATTRS = kadgem,sectie,percnr
    TRIM_TO_NONE = Yes
    TRIM_TYPE = Both
    -> AttributeCreator
AttributeCreator
    ATTR_LIST = kadgem_sectie_pnr,@Value(kadgem).@Value(sectie).@Value(percnr),NameSpace,NL.KAD.CP
    -> AreaCalculator
Note: Berekenen oppervlak en afronden op gehele meters
AreaCalculator
    AREA_ATTR = _area
    AREA_TYPE = Plane Area
    MULT = 1
    -> AttributeRounder
AttributeRounder
    SRC_ATTRS = _area
    ROUND_TYPE = nearest
    PLACES = 0
    -> CsmapReprojector
Note: Reprojectie naar EPSG:4258
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> AttributeCopier
AttributeCopier
    ATTR_LIST = kadgem_sectie_pnr,inspireId.Identifier.localId,"",NameSpace,inspireId.Identifier.namespace,"",gid,gml_id,"",_area,areaValue,"",kadgem_sectie_pnr,gml_identifier,"","",areaValue.uom,m2,kadgem_sectie_pnr,label,"",kadgem_sectie_pnr,nationalCadastralReference,""
    -> InsidePointReplacer
    -> GeometryPropertySetter
InsidePointReplacer
    INSIDEPOINT -> GeometryPropertySetter_2
GeometryPropertySetter_2
    OVERWRITE_CHOICE = Yes
    SETTYPE_PARAM = Geometry Name
    GEOM_NAME_FIELD = referencePoint
    SET -> Aggregator
GeometryPropertySetter
    OVERWRITE_CHOICE = Yes
    SETTYPE_PARAM = Geometry Name
    GEOM_NAME_FIELD = geometry
    SET -> Aggregator
Aggregator
    GROUP_BY = gid
    MODE = Geometry - Assemble One Level
    ACCUM_ATTRS_NAME = Yes
    SEP = ,
    AGGREGATE_TYPE = Multiple Geometry
    ORDERED = No
    AGGREGATE -> CadastralParcel (writer INSPIRE_1)
CadastralParcel (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, areaValue xml_real64, areaValue.nilReason xml_buffer, areaValue.uom xml_buffer, areaValue.xsi_nil xml_boolean, beginLifespanVersion xml_datetime, beginLifespanVersion.nilReason xml_buffer, beginLifespanVersion.xsi_nil xml_boolean, endLifespanVersion xml_datetime, endLifespanVersion.nilReason xml_buffer,
      endLifespanVersion.xsi_nil xml_boolean, geometry xml_geometry, inspireId.Identifier.localId xml_buffer, inspireId.Identifier.namespace xml_buffer, inspireId.Identifier.versionId xml_buffer, inspireId.Identifier.versionId.nilReason xml_buffer, inspireId.Identifier.versionId.xsi_nil xml_boolean, label xml_buffer, nationalCadastralReference xml_buffer, referencePoint xml_geometry, validFrom xml_datetime, validFrom.nilReason xml_buffer, validFrom.xsi_nil xml_boolean, validTo xml_datetime, validTo.nilReason xml_buffer, validTo.xsi_nil xml_boolean, basicPropertyUnit{}.owns xml_boolean, basicPropertyUnit{}.nilReason xml_buffer, basicPropertyUnit{}.gml_remoteSchema xml_buffer, basicPropertyUnit{}.xlink_href xml_buffer, basicPropertyUnit{}.xsi_nil xml_boolean, administrativeUnit.owns xml_boolean, administrativeUnit.nilReason xml_buffer, administrativeUnit.gml_remoteSchema xml_buffer, administrativeUnit.xlink_href xml_buffer, administrativeUnit.xsi_nil xml_boolean, zoning.owns xml_boolean, zoning.nilReason xml_buffer, zoning.gml_remoteSchema xml_buffer, zoning.xlink_href xml_buffer,
      zoning.xsi_nil xml_boolean

Bookmark: postgis data perceelvlakken
Note: Lezen tabel brk.perceel_imp
brk.perceel_imp (reader POSTGIS_1)
    attributes: gid int4,PRIKEY, perceelnr varchar(17), geom_valid bool
    -> AttributeKeeper_2
