FME workspace BAG_INSPIRE_ADR_TFN.fmw

Parameters:
- LOG_FILE = $(FME_MF_DIR)test.log   # Log File
- MAX_FEATURES =   # Max Features to Read

Readers:
- POSTGIS_1: POSTGIS from pdok

Writers:
- POSTGIS_2: POSTGIS to pdok

bag.openbareruimteactueelbestaand (reader POSTGIS_1)
    attributes: gid int4, identificatie float8, aanduidingrecordinactief bool, aanduidingrecordcorrectie int4, officieel bool, inonderzoek bool, documentnummer varchar(20), documentdatum date, openbareruimtenaam varchar(80), openbareruimtestatus char(4), openbareruimtetype char(4), gerelateerdewoonplaats float8, verkorteopenbareruimtenaam varchar(80), begindatumtijdvakgeldigheid timestamp, einddatumtijdvakgeldigheid timestamp
    -> AttributeKeeper_3
AttributeKeeper_3
    KEEP_ATTRS = identificatie,openbareruimtenaam,begindatumtijdvakgeldigheid,einddatumtijdvakgeldigheid
    -> DuplicateRemover_4
DuplicateRemover_4
    KEYATTR = identificatie
    UNIQUE -> DateFormatter_4
DateFormatter_4
    DATE_ATTR = begindatumtijdvakgeldigheid,einddatumtijdvakgeldigheid
    FMT = %Y-%m-%dT00:00:00
    -> XMLTemplater_3
XMLTemplater_3
    RESULT_ATTRIBUTE = ADRESMEMBER
    ROOT_QUERY_EXPR:
       <ad:ThoroughfareName xmlns:base="urn:x-inspire:specification:gmlas:BaseTypes:3.2" xmlns:ad="urn:x-inspire:specification:gmlas:Addresses:3.0" xmlns:gn="urn:x-inspire:specification:gmlas:GeographicalNames:3.0" xmlns:xlink="http://www.w3.org/1999/xlink" xmlns:xsi="http://www.w3.org/2001/XMLSchema-instance" xmlns:gml="http://www.opengis.net/gml/3.2" xsi:schemaLocation="urn:x-inspire:specification:gmlas:BaseTypes:3.2 http://inspire.ec.europa.eu/schemas/base/3.2/BaseTypes.xsd                      urn:x-inspire:specification:gmlas:Addresses:3.0 http://inspire.ec.europa.eu/schemas/ad/3.0/Addresses.xsd                      urn:x-inspire:specification:gmlas:GeographicalNames:3.0 http://inspire.ec.europa.eu/schemas/gn/3.0/GeographicalNames.xsd" gml:id="NL.KAD.BAG.AD.ThoroughfareName.{fme:get-attribute("identificatie")}">
         <gml:identifier codeSpace="http://inspire.jrc.ec.europa.eu/">
           urn:x-inspire:object:id:NL.KAD.BAG.AD.ThoroughfareName.{fme:get-attribute('identificatie')}
         </gml:identifier>
         <ad:inspireId>
          <base:Identifier>
            <base:localId>{fme:get-attribute('identificatie')}</base:localId>
            <base:namespace>NL.KAD.BAG.AD.ThoroughfareName</base:namespace>
          </base:Identifier>
         </ad:inspireId>
        <ad:beginLifespanVersion xsi:nil="true" nilReason="other:unpopulated"></ad:beginLifespanVersion>
        <ad:endLifespanVersion xsi:nil="true" nilReason="other:unpopulated"></ad:endLifespanVersion>
        <ad:status xsi:nil="true" nilReason="other:unpopulated"></ad:status>
        <ad:validFrom>{fme:get-attribute("begindatumtijdvakgeldigheid")}</ad:validFrom>
        <ad:validTo xsi:nil="true" nilReason="other:unpopulated"></ad:validTo>
        <ad:name>
          <gn:GeographicalName>
            <gn:language>NL</gn:language>
            <gn:nativeness>endonym</gn:nativeness>
            <gn:nameStatus  nilReason="other:unpopulated" xsi:nil="true"></gn:nameStatus>
            <gn:sourceOfName>Kadaster</gn:sourceOfName>
            <gn:pronunciation nilReason="other:unpopulated" xsi:nil="true"/>
            <gn:spelling>
              <gn:SpellingOfName>
                <gn:text>{fme:get-attribute('openbareruimtenaam')}</gn:text>
                  <gn:script>Latn</gn:script>
              </gn:SpellingOfName>
            </gn:spelling>
          </gn:GeographicalName>
        </ad:name>
       </ad:ThoroughfareName>
    VISIBLE_QUERY_VALIDATE = No
    OUTPUT_XML_HEADER = No
    -> AttributeCreator_4
AttributeCreator_4
    ATTR_LIST = ft_type,16
    -> AttributeExpressionRemover_4
AttributeExpressionRemover_4
    ATTR_EXP = postgis*
    -> AttributeCopier_4
AttributeCopier_4
    ATTR_LIST = gml_id,identificatie,binary_object,ADRESMEMBER
    -> StringConcatenator_4
StringConcatenator_4
    PARM_LINE = fme_basicstring:31%14:NL.KAD.BAG.AD.ThoroughfareName.@Value(gml_id)
    VAL_ATTR = gml_id
    -> GeometryRemover_3
GeometryRemover_3
    -> StringReplacer
StringReplacer
    SRC_ATTRS = binary_object
    REGEXP = no
    CASE = no
    FIND_TEXT = xmlns:base="urn:x-inspire:specification:gmlas:BaseTypes:3.2" xmlns:ad="urn:x-inspire:specification:gmlas:Addresses:3.0" xmlns:gn="urn:x-inspire:specification:gmlas:GeographicalNames:3.0" xmlns:xlink="http://www.w3.org/1999/xlink" xmlns:xsi="http://www.w3.org/2001/XMLSchema-instance" xmlns:gml="http://www.opengis.net/gml/3.2" xsi:schemaLocation="urn:x-inspire:specification:gmlas:BaseTypes:3.2 http://inspire.ec.europa.eu/schemas/base/3.2/BaseTypes.xsd                      urn:x-inspire:specification:gmlas:Addresses:3.0 http://inspire.ec.europa.eu/schemas/ad/3.0/Addresses.xsd                      urn:x-inspire:specification:gmlas:GeographicalNames:3.0 http://inspire.ec.europa.eu/schemas/gn/3.0/GeographicalNames.xsd"
    -> BinaryEncoder
BinaryEncoder
    ENCODING_TYPE = HEX
    ATTR_TO_ENCODE = binary_object
    DEST_ATTR = binary_object
    -> inspire_ad.gml_objects (writer POSTGIS_2)
inspire_ad.gml_objects (writer POSTGIS_2)
    attributes: id serial,PRIKEY, gml_id text,none, ft_type int2, binary_object bytea
