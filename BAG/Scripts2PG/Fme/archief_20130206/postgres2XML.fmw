FME workspace postgres2XML.fmw

Parameters:
- XML_DIR = H:\Projects\PDOK\BAG\Scripts2PG\XML_uit   # Fanout Directory
- LOG_FILE = H:\Projects\PDOK\BAG\Scripts2PG\Log\BAG_postgres2XML_TFN_5.log   # Log File
- AANTAL = 5   # Number Of Records To Fetch At A Time
- TYPE = 16   # Feature type

Readers:
- POSTGRES_1: POSTGRES from pdok

Writers:
- TEXTLINE_1: TEXTLINE to H:\Projects\PDOK\Scripts2PG\XML_uit\test_5.xml

inspire_ad_blob.gml_objects (reader POSTGRES_1)
    attributes: id serial,PRIKEY, gml_id text,PRIKEY, ft_type int2, binary_object bytea, gml_bounded_by char(80),GIST
    -> BinaryDecoder
BinaryDecoder
    DEST_ATTR = _decoded
    ATTR_TO_DECODE = binary_object
    ENCODING_TYPE = HEX
    ATTR_ENCODING = utf-8
    -> StringConcatenator
StringConcatenator
    PARM_LINE:
      fme_basicstring:38%1%16:<?xml version="1.0" encoding="UTF-8"?>
      @Value(_decoded)
    VAL_ATTR = _decoded
    -> text_line (writer TEXTLINE_1)
text_line (writer TEXTLINE_1)
    attributes: text_line_data buffer
