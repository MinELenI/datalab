FME workspace BAG_INSPIRE_ADR_PDC.fmw

Parameters:
- LOG_FILE = $(FME_MF_DIR)test.log   # Log File
- MAX_FEATURES =   # Max Features to Read

Readers:
- POSTGIS_1: POSTGIS from pdok

Writers:
- POSTGIS_2: POSTGIS to pdok

bag.verblijfsobject (reader POSTGIS_1)
    attributes: postcode varchar(6)
    -> GeometryRemover
GeometryRemover
    -> XMLTemplater_7
XMLTemplater_7
    RESULT_ATTRIBUTE = ADRESMEMBER
    ROOT_QUERY_EXPR:
       <ad:PostalDescriptor xmlns:base="urn:x-inspire:specification:gmlas:BaseTypes:3.2" xmlns:ad="urn:x-inspire:specification:gmlas:Addresses:3.0" xmlns:gn="urn:x-inspire:specification:gmlas:GeographicalNames:3.0" xmlns:xlink="http://www.w3.org/1999/xlink" xmlns:xsi="http://www.w3.org/2001/XMLSchema-instance" xmlns:gml="http://www.opengis.net/gml/3.2" xsi:schemaLocation="urn:x-inspire:specification:gmlas:BaseTypes:3.2 http://inspire.ec.europa.eu/schemas/base/3.2/BaseTypes.xsd                      urn:x-inspire:specification:gmlas:Addresses:3.0 http://inspire.ec.europa.eu/schemas/ad/3.0/Addresses.xsd                      urn:x-inspire:specification:gmlas:GeographicalNames:3.0 http://inspire.ec.europa.eu/schemas/gn/3.0/GeographicalNames.xsd" gml:id="NL.KAD.BAG.AD.PostalDescriptor.{fme:get-attribute('postcode')}">
         <gml:identifier codeSpace="http://inspire.jrc.ec.europa.eu/">
             urn:x-inspire:object:id:NL.KAD.BAG.AD.PostalDescriptor.{fme:get-attribute('postcode')}
         </gml:identifier>
         <ad:inspireId>
           <base:Identifier>
           <base:localId>{fme:get-attribute('postcode')}</base:localId>
           <base:namespace>NL.KAD.BAG.AD.PostalDescriptor</base:namespace>
           </base:Identifier>
         </ad:inspireId>
        <ad:beginLifespanVersion xsi:nil="true" nilReason="other:unpopulated"></ad:beginLifespanVersion>
        <ad:endLifespanVersion xsi:nil="true" nilReason="other:unpopulated"></ad:endLifespanVersion>
        <ad:status xsi:nil="true" nilReason="other:unpopulated"></ad:status>
        <ad:validFrom xsi:nil="true" nilReason="other:unpopulated"></ad:validFrom>
        <ad:validTo xsi:nil="true" nilReason="other:unpopulated"></ad:validTo>
        <ad:postName>
          <gn:GeographicalName>
            <gn:language nilReason="">NL</gn:language>
            <gn:nativeness>endonym</gn:nativeness>
            <gn:nameStatus  nilReason="other:unpopulated" xsi:nil="true"></gn:nameStatus>
            <gn:sourceOfName>Kadaster</gn:sourceOfName>
            <gn:pronunciation nilReason="other:unpopulated" xsi:nil="true"/>
            <gn:spelling>
              <gn:SpellingOfName>
                <gn:text>{fme:get-attribute('postcode')}</gn:text>
                  <gn:script>Latn</gn:script>
              </gn:SpellingOfName>
            </gn:spelling>
          </gn:GeographicalName>
        </ad:postName>
        <ad:postCode>{fme:get-attribute('postcode')}</ad:postCode>
       </ad:PostalDescriptor>
    VISIBLE_QUERY_VALIDATE = No
    OUTPUT_XML_HEADER = No
    -> AttributeCreator_2
AttributeCreator_2
    ATTR_LIST = ft_type,15
    -> AttributeExpressionRemover_2
AttributeExpressionRemover_2
    ATTR_EXP = postgis*
    -> AttributeCopier_2
AttributeCopier_2
    ATTR_LIST = gml_id,postcode,binary_object,ADRESMEMBER
    -> StringConcatenator_2
StringConcatenator_2
    PARM_LINE = fme_basicstring:31%14:NL.KAD.BAG.AD.PostalDescriptor.@Value(gml_id)
    VAL_ATTR = gml_id
    -> inspire_ad.gml_objects (writer POSTGIS_2)
inspire_ad.gml_objects (writer POSTGIS_2)
    attributes: id serial,PRIKEY, gml_id text,none, ft_type int2, binary_object bytea
StringReplacer [off]
    SRC_ATTRS = binary_object
    REGEXP = no
    CASE = no
    FIND_TEXT = xmlns:base="urn:x-inspire:specification:gmlas:BaseTypes:3.2" xmlns:ad="urn:x-inspire:specification:gmlas:Addresses:3.0" xmlns:gn="urn:x-inspire:specification:gmlas:GeographicalNames:3.0" xmlns:xlink="http://www.w3.org/1999/xlink" xmlns:xsi="http://www.w3.org/2001/XMLSchema-instance" xmlns:gml="http://www.opengis.net/gml/3.2" xsi:schemaLocation="urn:x-inspire:specification:gmlas:BaseTypes:3.2 http://inspire.ec.europa.eu/schemas/base/3.2/BaseTypes.xsd                      urn:x-inspire:specification:gmlas:Addresses:3.0 http://inspire.ec.europa.eu/schemas/ad/3.0/Addresses.xsd                      urn:x-inspire:specification:gmlas:GeographicalNames:3.0 http://inspire.ec.europa.eu/schemas/gn/3.0/GeographicalNames.xsd"
