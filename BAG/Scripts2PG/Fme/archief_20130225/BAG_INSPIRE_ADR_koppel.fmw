FME workspace BAG_INSPIRE_ADR_koppel.fmw

Parameters:
- LOG_FILE = $(FME_MF_DIR)test.log   # Log File

Readers:
- POSTGRES_1: POSTGRES from pdok

Writers:
- POSTGRES_2: POSTGRES to pdok

bag.nummeraanduiding (reader POSTGRES_1)
    attributes: identificatie float8,BTREE, postcode varchar(6),BTREE, gerelateerdeopenbareruimte float8,BTREE, gerelateerdewoonplaats float8,BTREE
    -> AttributeCopier
AttributeCopier
    ATTR_LIST = adres,identificatie,openbareruimte,gerelateerdeopenbareruimte,woonplaats,gerelateerdewoonplaats
    -> inspire_ad.adres_koppel (writer POSTGRES_2)
inspire_ad.adres_koppel (writer POSTGRES_2)
    attributes: adres float8,BTREE, openbareruimte float8, woonplaats float8, postcode varchar(6)
