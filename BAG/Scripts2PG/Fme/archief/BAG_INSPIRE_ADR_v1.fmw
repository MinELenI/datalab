FME workspace BAG_INSPIRE_ADR_v1.fmw

Parameters:
- LOG_FILE = $(FME_MF_DIR)test.log   # Log File
- DestDataset_POSTGIS = pdok   # Destination PostGIS Dataset

Readers:
- POSTGIS_1: POSTGIS from pdok

Writers:
- POSTGIS_2: POSTGIS to $(DestDataset_POSTGIS)

bag.verblijfsobject (reader POSTGIS_1)
    attributes: gid serial,PRIKEY, identificatie float8,BTREE, begindatumtijdvakgeldigheid timestamp, einddatumtijdvakgeldigheid timestamp, gerelateerdeopenbareruimte float8, openbareruimtenaam varchar(80), gerelateerdewoonplaats float8, woonplaatsnaam varchar(80), huisnummer float8, huisletter varchar(1), huisnummertoevoeging varchar(4), nummeraanduidingstatus varchar(4), postcode varchar(6)
    -> CoordinateExtractor
CoordinateExtractor
    Z_DEFAULT = -9999
    IND = 0
    Y_ATTR = _y
    X_ATTR = _x
    Z_ATTR = _z
    -> AttributeReprojector
AttributeReprojector
    DEST = EPSG:4258
    XATTR = _x
    SOURCE = EPSG:28992
    YATTR = _y
    -> Tester
Tester
    TEST_DESCRIPTION = ""
    TEST_CLAUSE:
      TEST "_x" NOT_ATTRIBUTE_IS_EMPTY "<Unused>"
      TEST "_x" NOT_ATTRIBUTE_IS_NULL "<Unused>"
    BOOL_OP = AND
    TEST_MODE = Automatic
    PASSED -> XMLTemplater_2
Note: Versie 2 naar Postgres
XMLTemplater_2
    OUTPUT_XML_HEADER = No
    VISIBLE_QUERY_VALIDATE = No
    ROOT_QUERY_EXPR:
      <ad:Address xmlns:ad="urn:x-inspire:specification:gmlas:Addresses:3.0" xmlns:au="urn:x-inspire:specification:gmlas:AdministrativeUnits:3.0" xmlns:base="urn:x-inspire:specification:gmlas:BaseTypes:3.2" xmlns:bui="urn:x-inspire:specification:gmlas:Buildings:0.0" xmlns:cp="urn:x-inspire:specification:gmlas:CadastralParcels:3.0" xmlns:gml="http://www.opengis.net/gml/3.2" xmlns:gn="urn:x-inspire:specification:gmlas:GeographicalNames:3.0" xmlns:tn="urn:x-inspire:specification:gmlas:CommonTransportElements:3.0" xmlns:gco="http://www.isotc211.org/2005/gco" xmlns:xlink="http://www.w3.org/1999/xlink" xmlns:gmd="http://www.isotc211.org/2005/gmd" xmlns:gsr="http://www.isotc211.org/2005/gsr" xmlns:gts="http://www.isotc211.org/2005/gts" xmlns:tn-a="urn:x-inspire:specification:gmlas:AirTransportNetwork:3.0" xmlns:stat="urn:x-inspire:specification:gmlas:StatisticalUnits:0.0" xmlns:net="urn:x-inspire:specification:gmlas:Network:3.2" xmlns:gss="http://www.isotc211.org/2005/gss" gml:id="">
        <gml:metaDataProperty about="" nilReason="" gml:remoteSchema="" xlink:type="simple" xlink:href="" xlink:role="" xlink:arcrole="" xlink:title="" xlink:show="" xlink:actuate="">
          <gml:GenericMetaData gml:id=""></gml:GenericMetaData>
        </gml:metaDataProperty>
        <gml:description nilReason="" gml:remoteSchema="" xlink:type="simple" xlink:href="" xlink:role="" xlink:arcrole="" xlink:title="" xlink:show="" xlink:actuate=""></gml:description>
        <gml:descriptionReference owns="false" nilReason="" gml:remoteSchema="" xlink:type="simple" xlink:href="" xlink:role="" xlink:arcrole="" xlink:title="" xlink:show="" xlink:actuate=""/>
        <gml:identifier codeSpace=""></gml:identifier>
        <gml:name codeSpace=""></gml:name>
        <gml:boundedBy nilReason=""></gml:boundedBy>
        <gml:location nilReason="" gml:remoteSchema="" xlink:type="simple" xlink:href="" xlink:role="" xlink:arcrole="" xlink:title="" xlink:show="" xlink:actuate=""></gml:location>
        <ad:inspireId>
          <base:Identifier>
            <base:localId>{fme:get-attribute("identificatie")}</base:localId>
            <base:namespace>NL.KAD.BAG</base:namespace>
            <base:versionId nilReason=""></base:versionId>
          </base:Identifier>
        </ad:inspireId>
        <ad:alternativeIdentifier nilReason=""></ad:alternativeIdentifier>
        <ad:position>
          <ad:GeographicPosition>
            <ad:geometry nilReason="" gml:remoteSchema="" xlink:type="simple" xlink:href="" xlink:role="" xlink:arcrole="" xlink:title="" xlink:show="" xlink:actuate="" owns="false">
              <gml:Point srsName="EPSG:4258" srsDimension="2" axisLabels="" uomLabels="" gml:id="{fme:get-attribute("gid")}">
                <gml:metaDataProperty about="" nilReason="" gml:remoteSchema="" xlink:type="simple" xlink:href="" xlink:role="" xlink:arcrole="" xlink:title="" xlink:show="" xlink:actuate="">
                  <gml:GenericMetaData gml:id=""></gml:GenericMetaData>
                </gml:metaDataProperty>
                <gml:description nilReason="" gml:remoteSchema="" xlink:type="simple" xlink:href="" xlink:role="" xlink:arcrole="" xlink:title="" xlink:show="" xlink:actuate=""></gml:description>
                <gml:descriptionReference owns="false" nilReason="" gml:remoteSchema="" xlink:type="simple" xlink:href="" xlink:role="" xlink:arcrole="" xlink:title="" xlink:show="" xlink:actuate=""/>
                <gml:identifier codeSpace="">{fme:get-attribute("gid")}</gml:identifier>
                <gml:name codeSpace="">{fme:get-attribute("_x")} {fme:get-attribute("_y")}</gml:name>
              </gml:Point>
            </ad:geometry>
            <ad:specification nilReason="" codeSpace=""></ad:specification>
            <ad:method nilReason="" codeSpace=""></ad:method>
            <ad:default></ad:default>
          </ad:GeographicPosition>
        </ad:position>
        <ad:status nilReason="" codeSpace=""></ad:status>
        <ad:locator>
          <ad:AddressLocator>
            <ad:designator>
              <ad:LocatorDesignator>
                <ad:designator></ad:designator>
                <ad:type codeSpace=""></ad:type>
              </ad:LocatorDesignator>
            </ad:designator>
            <ad:name>
              <ad:LocatorName>
                <ad:name>
                  <gn:GeographicalName>
                    <gn:language nilReason="">NL</gn:language>
                    <gn:nativeness nilReason="" codeSpace=""></gn:nativeness>
                    <gn:nameStatus nilReason="" codeSpace="">{fme:get-attribute("nummeraanduidingstatus")}</gn:nameStatus>
                    <gn:sourceOfName nilReason=""></gn:sourceOfName>
                    <gn:pronunciation nilReason="">
                      <gn:PronunciationOfName>
                        <gn:pronunciationSoundLink nilReason=""></gn:pronunciationSoundLink>
                        <gn:pronunciationIPA nilReason=""></gn:pronunciationIPA>
                      </gn:PronunciationOfName>
                    </gn:pronunciation>
                    <gn:spelling>
                      <gn:SpellingOfName>
                        <gn:text>{fme:get-attribute("huisnummer")} {fme:get-attribute("huisletter")} {fme:get-attribute("huisnummertoevoeging")}</gn:text>
                        <gn:script nilReason=""></gn:script>
                        <gn:transliterationScheme nilReason=""></gn:transliterationScheme>
                      </gn:SpellingOfName>
                    </gn:spelling>
                    <gn:grammaticalGender nilReason="" codeSpace=""></gn:grammaticalGender>
                    <gn:grammaticalNumber nilReason="" codeSpace=""></gn:grammaticalNumber>
                  </gn:GeographicalName>
                </ad:name>
                <ad:type codeSpace="">2</ad:type>
              </ad:LocatorName>
            </ad:name>
            <ad:level codeSpace=""></ad:level>
            <ad:withinScopeOf owns="false" nilReason="" gml:remoteSchema="" xlink:type="simple" xlink:href="" xlink:role="" xlink:arcrole="" xlink:title="" xlink:show="" xlink:actuate=""/>
          </ad:AddressLocator>
        </ad:locator>
        <ad:validFrom nilReason="">{fme:get-attribute("begindatumtijdvakgeldigheid")}</ad:validFrom>
        <ad:validTo nilReason="">{fme:get-attribute("einddatumtijdvakgeldigheid")}</ad:validTo>
        <ad:beginLifespanVersion nilReason=""></ad:beginLifespanVersion>
        <ad:endLifespanVersion nilReason=""></ad:endLifespanVersion>
        <ad:parcel owns="false" nilReason="" gml:remoteSchema="" xlink:type="simple" xlink:href="" xlink:role="" xlink:arcrole="" xlink:title="" xlink:show="" xlink:actuate=""/>
        <ad:parentAddress owns="false" nilReason="" gml:remoteSchema="" xlink:type="simple" xlink:href="" xlink:role="" xlink:arcrole="" xlink:title="" xlink:show="" xlink:actuate=""/>
        <ad:building owns="false" nilReason="" gml:remoteSchema="" xlink:type="simple" xlink:href="" xlink:role="" xlink:arcrole="" xlink:title="" xlink:show="" xlink:actuate=""/>
        <ad:component nilReason="" gml:remoteSchema="" xlink:type="simple" xlink:href="" xlink:role="" xlink:arcrole="" xlink:title="" xlink:show="" xlink:actuate="" owns="false"/>
      </ad:Address>
    RESULT_ATTRIBUTE = ADRESMEMBER
    -> AttributeCreator
AttributeCreator
    ATTR_LIST = ft_type,12
    -> AttributeExpressionRemover
AttributeExpressionRemover
    ATTR_EXP = postgis*
    -> 2DForcer
2DForcer
    2D -> AttributeCopier
AttributeCopier
    ATTR_LIST = id,gid,gml_id,identificatie,binary_object,ADRESMEMBER
    -> inspire_ad_blob.gml_objects (writer POSTGIS_2)
inspire_ad_blob.gml_objects (writer POSTGIS_2)
    attributes: id serial,PRIKEY, gml_id text,PRIKEY, ft_type int2, binary_object bytea

Bookmark: postgis data verblijfsobject
Note: bag_aveen_120530.verblijfsobject
