FME workspace postgres2XML_v2.fmw

Parameters:
- SourceDataset_POSTGRES = pdok   # Source PostgreSQL Dataset
- DestDataset_TEXTLINE = H:\Projects\PDOK\Scripts2PG\XML_uit\test_5.xml   # Destination Text File

Readers:
- POSTGRES_1: POSTGRES from $(SourceDataset_POSTGRES)

Writers:
- TEXTLINE_1: TEXTLINE to $(DestDataset_TEXTLINE)

Creator
    GEOMTYPE = Geometry Object
    NUM = 1
    CREATED -> UUIDGenerator
UUIDGenerator
    UUID_ATTR = _guid
    -> AttributeCreator
AttributeCreator
    ATTR_LIST:
      header,<?xml version="1.0" encoding="UTF-8"?>
      <base:SpatialDataSet xmlns:ad="urn:x-inspire:specification:gmlas:Addresses:3.0" xmlns:au="urn:x-inspire:specification:gmlas:AdministrativeUnits:3.0" xmlns:base="urn:x-inspire:specification:gmlas:BaseTypes:3.2" xmlns:bui="urn:x-inspire:specification:gmlas:Buildings:0.0" xmlns:cp="urn:x-inspire:specification:gmlas:CadastralParcels:3.0" xmlns:gml="http://www.opengis.net/gml/3.2" xmlns:gn="urn:x-inspire:specification:gmlas:GeographicalNames:3.0" xmlns:tn="urn:x-inspire:specification:gmlas:CommonTransportElements:3.0" xmlns:gco="http://www.isotc211.org/2005/gco" xmlns:xlink="http://www.w3.org/1999/xlink" xmlns:gmd="http://www.isotc211.org/2005/gmd" xmlns:gsr="http://www.isotc211.org/2005/gsr" xmlns:gts="http://www.isotc211.org/2005/gts" xmlns:tn-a="urn:x-inspire:specification:gmlas:AirTransportNetwork:3.0" xmlns:stat="urn:x-inspire:specification:gmlas:StatisticalUnits:0.0" xmlns:net="urn:x-inspire:specification:gmlas:Network:3.2" xmlns:gss="http://www.isotc211.org/2005/gss" gml:id="NL.KAD.BAG">
        <gml:metaDataProperty about="" nilReason="" gml:remoteSchema="" xlink:type="simple" xlink:href="" xlink:role="" xlink:arcrole="" xlink:title="" xlink:show="none" xlink:actuate="none">
          <gml:GenericMetaData gml:id="NL.KAD.BAG.@Value(_guid)1"></gml:GenericMetaData>
        </gml:metaDataProperty>
        <gml:description nilReason="" gml:remoteSchema="" xlink:type="simple" xlink:href="" xlink:role="" xlink:arcrole="" xlink:title="" xlink:show="none" xlink:actuate="none"></gml:description>
        <gml:descriptionReference owns="false" nilReason="" gml:remoteSchema="" xlink:type="simple" xlink:href="" xlink:role="" xlink:arcrole="" xlink:title="" xlink:show="none" xlink:actuate="none"/>
        <gml:identifier codeSpace=""></gml:identifier>
        <gml:name codeSpace=""></gml:name>
        <gml:boundedBy nilReason="">
         <gml:Envelope srsName="EPSG:4258">
          <gml:lowerCorner>4.0 50.0</gml:lowerCorner>
          <gml:upperCorner>6.0 53.0</gml:upperCorner>
         </gml:Envelope>
        </gml:boundedBy>
        <base:identifier>
          <base:Identifier>
            <base:localId>0</base:localId>
            <base:namespace>NL.KAD.BAG</base:namespace>
            <base:versionId nilReason=""></base:versionId>
          </base:Identifier>
         </base:identifier>
    -> text_line (writer TEXTLINE_1)
inspire_ad_blob.gml_objects (reader POSTGRES_1)
    attributes: id serial,PRIKEY, gml_id text,PRIKEY, ft_type int2, binary_object bytea, gml_bounded_by char(80),GIST
    -> Sampler
Sampler
    RATE = 1
    SAMPLE_TYPE_LONG = First N Features
    SAMPLED -> TextDecoder
TextDecoder
    DEST_ATTR = _decoded
    STRING_TO_DECODE = @Value(binary_object)
    ENCODING_TYPE = HEX
    ATTR_ENCODING = utf-8
    -> text_line (writer TEXTLINE_1)
Creator_2
    GEOMTYPE = Geometry Object
    NUM = 1
    CREATED -> AttributeCreator_2
AttributeCreator_2
    ATTR_LIST = footer,</base:SpatialDataSet>
    -> text_line (writer TEXTLINE_1)
text_line (writer TEXTLINE_1)
    attributes: text_line_data buffer
