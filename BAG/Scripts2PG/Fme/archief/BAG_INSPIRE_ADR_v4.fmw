FME workspace BAG_INSPIRE_ADR_v4.fmw

Parameters:
- LOG_FILE = $(FME_MF_DIR)test.log   # Log File
- DestDataset_POSTGIS = pdok   # Destination PostGIS Dataset

Readers:
- POSTGIS_1: POSTGIS from pdok

Writers:
- POSTGIS_2: POSTGIS to $(DestDataset_POSTGIS)

bag.verblijfsobject (reader POSTGIS_1)
    attributes: gid serial,PRIKEY, identificatie float8,BTREE, begindatumtijdvakgeldigheid timestamp, einddatumtijdvakgeldigheid timestamp, gerelateerdeopenbareruimte float8, openbareruimtenaam varchar(80), gerelateerdewoonplaats float8, woonplaatsnaam varchar(80), huisnummer float8, huisletter varchar(1), huisnummertoevoeging varchar(4), nummeraanduidingstatus varchar(4), postcode varchar(6)
    -> CoordinateExtractor
CoordinateExtractor
    Z_DEFAULT = -9999
    IND = 0
    Y_ATTR = _y
    X_ATTR = _x
    Z_ATTR = _z
    -> AttributeReprojector
AttributeReprojector
    DEST = EPSG:4258
    XATTR = _x
    SOURCE = EPSG:28992
    YATTR = _y
    -> Tester
Tester
    TEST_DESCRIPTION = ""
    TEST_CLAUSE:
      TEST "_x" NOT_ATTRIBUTE_IS_EMPTY "<Unused>"
      TEST "_x" NOT_ATTRIBUTE_IS_NULL "<Unused>"
    BOOL_OP = AND
    TEST_MODE = Automatic
    PASSED -> DateFormatter
DateFormatter
    FMT = XML DateTime (%Y-%m-%dT%H:%M:%S)
    DATE_ATTR = begindatumtijdvakgeldigheid,einddatumtijdvakgeldigheid
    -> XMLTemplater_2
Note: Versie 2 naar Postgres
XMLTemplater_2
    OUTPUT_XML_HEADER = No
    VISIBLE_QUERY_VALIDATE = No
    ROOT_QUERY_EXPR:
      <base:member>
      <ad:Address  xmlns:ad="urn:x-inspire:specification:gmlas:Addresses:3.0" xmlns:au="urn:x-inspire:specification:gmlas:AdministrativeUnits:3.0" xmlns:base="urn:x-inspire:specification:gmlas:BaseTypes:3.2" xmlns:bui="urn:x-inspire:specification:gmlas:Buildings:0.0" xmlns:cp="urn:x-inspire:specification:gmlas:CadastralParcels:3.0" xmlns:gml="http://www.opengis.net/gml/3.2" xmlns:gn="urn:x-inspire:specification:gmlas:GeographicalNames:3.0" xmlns:tn="urn:x-inspire:specification:gmlas:CommonTransportElements:3.0" xmlns:gco="http://www.isotc211.org/2005/gco" xmlns:xlink="http://www.w3.org/1999/xlink" xmlns:gmd="http://www.isotc211.org/2005/gmd" xmlns:gsr="http://www.isotc211.org/2005/gsr" xmlns:gts="http://www.isotc211.org/2005/gts" xmlns:tn-a="urn:x-inspire:specification:gmlas:AirTransportNetwork:3.0" xmlns:stat="urn:x-inspire:specification:gmlas:StatisticalUnits:0.0" xmlns:net="urn:x-inspire:specification:gmlas:Network:3.2" xmlns:gss="http://www.isotc211.org/2005/gss" gml:id="NL.KAD.BAG.Address.{fme:get-attribute("identificatie")}">
          <ad:inspireId>
          <base:Identifier>
            <base:localId>{fme:get-attribute("identificatie")}</base:localId>
            <base:namespace>NL.KAD.BAG.Address</base:namespace>
            <base:versionId xsi:nil="true" nilReason="other:unpopulated"></base:versionId>
          </base:Identifier>
          </ad:inspireId>
        <ad:alternativeIdentifier xsi:nil="true" nilReason="other:unpopulated"></ad:alternativeIdentifier>
        <ad:position>
          <ad:GeographicPosition>
            <ad:geometry>
              <gml:Point srsName="urn:ogc:def:crs:EPSG::4258" srsDimension="2" gml:id="NL.KAD.BAG.Address.{fme:get-attribute("identificatie")}_P">
               <gml:pos>{fme:get-attribute("_y")} {fme:get-attribute("_x")}</gml:pos>
             </gml:Point>
            </ad:geometry>
          </ad:GeographicPosition>
        </ad:position>
        <ad:locator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute("huisnummer")} {fme:get-attribute("huisletter")} {fme:get-attribute("huisnummertoevoeging")}</gn:text>
                         <gn:script>Latn</gn:script>
                      </gn:SpellingOfName>
                    </gn:spelling>
                  </gn:GeographicalName>
                </ad:name>
                <ad:type>2</ad:type>
              </ad:LocatorName>
            </ad:name>
            <ad:level>1</ad:level>
          </ad:AddressLocator>
        </ad:locator>
        <ad:validFrom>{fme:get-attribute("begindatumtijdvakgeldigheid")}</ad:validFrom>
        <ad:validTo>{fme:get-attribute("einddatumtijdvakgeldigheid")}</ad:validTo>
        <ad:beginLifespanVersion xsi:nil="true" nilReason="other:unpopulated"></ad:beginLifespanVersion>
        <ad:endLifespanVersion xsi:nil="true" nilReason="other:unpopulated"></ad:endLifespanVersion>
        <ad:component xmlns:xlink="http://www.w3.org/1999/xlink"
                       xlink:href="#NL.KAD.BAG.AD.ThoroughfareName.{fme:get-attribute("gerelateerdeopenbareruimte")}"/>
        <ad:component xmlns:xlink="http://www.w3.org/1999/xlink" xlink:href="#NL.KAD.BAG.AD.AddressAreaName.{fme:get-attribute("gerelateerdewoonplaats")}"/>
        <ad:component xmlns:xlink="http://www.w3.org/1999/xlink"
                       xlink:href="#NL.KAD.BAG.AD.PostalDescriptor.{fme:get-attribute("postcode")}"/>
      </ad:Address>
      </base:member>
      <base:member>
       <ad:ThoroughfareName gml:id="NL.KAD.BAG.AD.ThoroughfareName.{fme:get-attribute("gerelateerdeopenbareruimte")}">
        <gml:identifier codeSpace="NL.KAD.BAG.AD.ThoroughfareName">{fme:get-attribute("gerelateerdeopenbareruimte")}</gml:identifier>
        <gml:name codeSpace=""></gml:name>
        <ad:beginLifespanVersion xsi:nil="true" nilReason="other:unpopulated"></ad:beginLifespanVersion>
        <ad:endLifespanVersion xsi:nil="true" nilReason="other:unpopulated"></ad:endLifespanVersion>
        <ad:status xsi:nil="true" nilReason="other:unpopulated"></ad:status>
        <ad:validFrom xsi:nil="true" nilReason="other:unpopulated"></ad:validFrom>
        <ad:validTo xsi:nil="true" nilReason="other:unpopulated"></ad:validTo>
        <ad:name>
          <gn:GeographicalName>
            <gn:language>NL</gn:language>
            <gn:nativeness>endonym</gn:nativeness>
            <gn:nameStatus  nilReason="other:unpopulated" xsi:nil="true"></gn:nameStatus>
            <gn:sourceOfName>Het Kadaster</gn:sourceOfName>
            <gn:pronunciation nilReason="other:unpopulated" xsi:nil="true"/>
            <gn:spelling>
              <gn:SpellingOfName>
                <gn:text>{fme:get-attribute("openbareruimtenaam")}</gn:text>
                  <gn:script>Latn</gn:script>
              </gn:SpellingOfName>
            </gn:spelling>
          </gn:GeographicalName>
        </ad:name>
       </ad:ThoroughfareName>
      </base:member>
      <base:member>
       <ad:PostalDescriptor gml:id="NL.KAD.BAG.AD.PostalDescriptor.{fme:get-attribute("postcode")}">
        <gml:identifier codeSpace="NL.KAD.BAG.AD.PostalDescriptor">{fme:get-attribute("postcode")}</gml:identifier>
        <ad:beginLifespanVersion xsi:nil="true" nilReason="other:unpopulated"></ad:beginLifespanVersion>
        <ad:endLifespanVersion xsi:nil="true" nilReason="other:unpopulated"></ad:endLifespanVersion>
        <ad:status xsi:nil="true" nilReason="other:unpopulated"></ad:status>
        <ad:validFrom xsi:nil="true" nilReason="other:unpopulated"></ad:validFrom>
        <ad:validTo xsi:nil="true" nilReason="other:unpopulated"></ad:validTo>
        <ad:postName>
          <gn:GeographicalName>
            <gn:language nilReason="">NL</gn:language>
            <gn:nativeness>endonym</gn:nativeness>
            <gn:nameStatus  nilReason="other:unpopulated" xsi:nil="true"></gn:nameStatus>
            <gn:sourceOfName>Het Kadaster</gn:sourceOfName>
            <gn:pronunciation nilReason="other:unpopulated" xsi:nil="true"/>
            <gn:spelling>
              <gn:SpellingOfName>
                <gn:text>{fme:get-attribute("postcode")}</gn:text>
                  <gn:script>Latn</gn:script>
              </gn:SpellingOfName>
            </gn:spelling>
          </gn:GeographicalName>
        </ad:postName>
        <ad:postCode>{fme:get-attribute("postcode")}</ad:postCode>
       </ad:PostalDescriptor>
      </base:member>
      <base:member>
       <ad:AddressAreaName  gml:id="NL.KAD.BAG.AD.AddressAreaName.{fme:get-attribute("gerelateerdewoonplaats")}">
          <gml:identifier codeSpace="http://inspire.jrc.ec.europa.eu/">
              urn:x-inspire:object:id:NL.KAD.BAG.AD.AddressAreaName.{fme:get-attribute("gerelateerdewoonplaats")}
          </gml:identifier>
          <ad:inspireId>
              <base:Identifier>
                  <base:localId>{fme:get-attribute("gerelateerdewoonplaats")}</base:localId>
                  <base:namespace>NL.KAD.BAG.AD.AddressAreaName</base:namespace>
              </base:Identifier>
          </ad:inspireId>
          <ad:beginLifespanVersion xsi:nil="true" nilReason="other:unpopulated"/>
          <ad:endLifespanVersion xsi:nil="true" nilReason="other:unpopulated"/>
          <ad:validFrom>2007-05-30T00:00:00</ad:validFrom>
          <ad:validTo xsi:nil="true" nilReason="other:unpopulated"/>
          <ad:name>
              <gn:GeographicalName>
                  <gn:language xsi:nil="true"/>
                  <gn:nativeness>endonym</gn:nativeness>
                  <gn:nameStatus  nilReason="other:unpopulated" xsi:nil="true"></gn:nameStatus>
                  <gn:sourceOfName>Het Kadaster</gn:sourceOfName>
                  <gn:pronunciation nilReason="other:unpopulated" xsi:nil="true"/>
                  <gn:spelling>
                      <gn:SpellingOfName>
                          <gn:text>{fme:get-attribute("woonplaatsnaam")}</gn:text>
                          <gn:script>Latn</gn:script>
                      </gn:SpellingOfName>
                  </gn:spelling>
                  <gn:grammaticalGender xsi:nil="true"/>
                  <gn:grammaticalNumber xsi:nil="true"/>
              </gn:GeographicalName>
          </ad:name>
          <ad:namedPlace xsi:nil="true"/>
       </ad:AddressAreaName>
      </base:member>
    RESULT_ATTRIBUTE = ADRESMEMBER
    -> AttributeCreator
AttributeCreator
    ATTR_LIST = ft_type,12
    -> AttributeExpressionRemover
AttributeExpressionRemover
    ATTR_EXP = postgis*
    -> 2DForcer
2DForcer
    2D -> Counter
Counter
    SCOPE = Global
    CNT_ATTR = _id
    DOMAIN = counter
    START = 1
    -> AttributeCopier
AttributeCopier
    ATTR_LIST = gml_id,identificatie,binary_object,ADRESMEMBER
    -> StringConcatenator
StringConcatenator
    PARM_LINE = fme_basicstring:19%14:NL.KAD.BAG.Address.@Value(gml_id)
    VAL_ATTR = gml_id
    -> DuplicateRemover
DuplicateRemover
    KEYATTR = gml_id
    UNIQUE -> inspire_ad_blob.gml_objects (writer POSTGIS_2)
inspire_ad_blob.gml_objects (writer POSTGIS_2)
    attributes: id serial,PRIKEY, gml_id text,none, ft_type int2, binary_object bytea

Bookmark: postgis data verblijfsobject
Note: bag_aveen_120530.verblijfsobject
