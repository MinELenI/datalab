FME workspace BAG_INSPIRE_ADR_ADR.fmw

Parameters:
- LOG_FILE = $(FME_MF_DIR)test.log   # Log File

Readers:
- POSTGIS_1: POSTGIS from pdok

Writers:
- POSTGIS_2: POSTGIS to pdok

bag.standplaats (reader POSTGIS_1)
    attributes: gid serial,PRIKEY, identificatie float8,BTREE, aanduidingrecordinactief bool, aanduidingrecordcorrectie int4, officieel bool, inonderzoek bool, begindatumtijdvakgeldigheid timestamp, einddatumtijdvakgeldigheid timestamp, documentnummer varchar(20), documentdatum date, hoofdadres float8, standplaatsstatus char(4), geom_valid bool
    -> CenterPointReplacer
bag.ligplaats (reader POSTGIS_1)
    attributes: gid serial,PRIKEY, identificatie float8,BTREE, aanduidingrecordinactief bool, aanduidingrecordcorrectie int4, officieel bool, inonderzoek bool, begindatumtijdvakgeldigheid timestamp, einddatumtijdvakgeldigheid timestamp, documentnummer varchar(20), documentdatum date, hoofdadres float8, ligplaatsstatus char(4), geom_valid bool
    -> CenterPointReplacer
CenterPointReplacer
    CENTERPOINT -> DuplicateRemover
bag.verblijfsobject (reader POSTGIS_1)
    attributes: gid serial,PRIKEY, identificatie float8,BTREE, begindatumtijdvakgeldigheid timestamp, einddatumtijdvakgeldigheid timestamp, gerelateerdeopenbareruimte float8, openbareruimtenaam varchar(80), gerelateerdewoonplaats float8, woonplaatsnaam varchar(80), huisnummer float8, huisletter varchar(1), huisnummertoevoeging varchar(4), nummeraanduidingstatus varchar(4), postcode varchar(6)
    -> DuplicateRemover
DuplicateRemover
    KEYATTR = identificatie
    UNIQUE -> CoordinateExtractor
CoordinateExtractor
    Z_DEFAULT = -9999
    IND = 0
    Y_ATTR = _y
    X_ATTR = _x
    Z_ATTR = _z
    -> AttributeReprojector
AttributeReprojector
    DEST = EPSG:4258
    XATTR = _x
    SOURCE = EPSG:28992
    YATTR = _y
    -> Tester
Tester
    TEST_DESCRIPTION = ""
    TEST_CLAUSE:
      TEST "_x" NOT_ATTRIBUTE_IS_EMPTY "<Unused>"
      TEST "_x" NOT_ATTRIBUTE_IS_NULL "<Unused>"
    BOOL_OP = AND
    TEST_MODE = Automatic
    PASSED -> DateFormatter
DateFormatter
    FMT = XML DateTime (%Y-%m-%dT%H:%M:%S)
    DATE_ATTR = begindatumtijdvakgeldigheid,einddatumtijdvakgeldigheid
    -> TestFilter
TestFilter
    TEST_LIST:
      BOOL_OP,AND,COMPOSITE_TEST,<Unused>,TEST_CLAUSE,"TEST ""huisnummer"" NOT_ATTRIBUTE_IS_NULL ""<Unused>""
      TEST ""huisletter"" NOT_ATTRIBUTE_IS_NULL ""<Unused>""
      TEST ""huisnummertoevoeging"" NOT_ATTRIBUTE_IS_NULL ""<Unused>""",Hnr_Hlt_Toev,BOOL_OP,AND,COMPOSITE_TEST,<Unused>,TEST_CLAUSE,"TEST ""huisnummer"" NOT_ATTRIBUTE_IS_NULL ""<Unused>""
      TEST ""huisletter"" NOT_ATTRIBUTE_IS_NULL ""<Unused>""
      TEST ""huisnummertoevoeging"" ATTRIBUTE_IS_NULL ""<Unused>""",Hnr_Hlt,BOOL_OP,AND,COMPOSITE_TEST,<Unused>,TEST_CLAUSE,"TEST ""huisnummer"" NOT_ATTRIBUTE_IS_NULL ""<Unused>""
      TEST ""huisletter"" ATTRIBUTE_IS_NULL ""<Unused>""
      TEST ""huisnummertoevoeging"" NOT_ATTRIBUTE_IS_NULL ""<Unused>""",Hnr_Toev,BOOL_OP,AND,COMPOSITE_TEST,<Unused>,TEST_CLAUSE,"TEST ""huisnummer"" NOT_ATTRIBUTE_IS_NULL ""<Unused>""
      TEST ""huisletter"" ATTRIBUTE_IS_NULL ""<Unused>""
      TEST ""huisnummertoevoeging"" ATTRIBUTE_IS_NULL ""<Unused>""",Hnr
    Hnr_Hlt_Toev -> XMLTemplater_2
    Hnr_Hlt -> XMLTemplater_4
    Hnr_Toev -> XMLTemplater_5
    Hnr -> XMLTemplater_6
XMLTemplater_2
    OUTPUT_XML_HEADER = No
    VISIBLE_QUERY_VALIDATE = No
    ROOT_QUERY_EXPR:
      <?xml version="1.0" encoding="UTF-8"?>
      <base:SpatialDataSet xmlns:base="urn:x-inspire:specification:gmlas:BaseTypes:3.2"
                           xmlns:ad="urn:x-inspire:specification:gmlas:Addresses:3.0"
                           xmlns:gn="urn:x-inspire:specification:gmlas:GeographicalNames:3.0"
                           xmlns:xlink="http://www.w3.org/1999/xlink"
                           xmlns:xsi="http://www.w3.org/2001/XMLSchema-instance"
                           xmlns:gml="http://www.opengis.net/gml/3.2"
                           xsi:schemaLocation="urn:x-inspire:specification:gmlas:BaseTypes:3.2 http://inspire.ec.europa.eu/schemas/base/3.2/BaseTypes.xsd
                           urn:x-inspire:specification:gmlas:Addresses:3.0 http://inspire.ec.europa.eu/schemas/ad/3.0/Addresses.xsd
                           urn:x-inspire:specification:gmlas:GeographicalNames:3.0 http://inspire.ec.europa.eu/schemas/gn/3.0/GeographicalNames.xsd"
                           gml:id="NL.KAD.BAG.AD">
          <base:identifier>
              <base:Identifier>
                  <base:localId>0</base:localId>
                  <base:namespace>NL.KAD.BAG.AD</base:namespace>
              </base:Identifier>
          </base:identifier>
          <base:metadata xsi:nil="true"/>
      <base:member>
      <ad:Address gml:id="NL.KAD.BAG.Address.{fme:get-attribute('identificatie')}">
          <gml:identifier codeSpace="http://inspire.jrc.ec.europa.eu/">
               urn:x-inspire:object:id:NL.KAD.BAG.AD.Address.{fme:get-attribute('identificatie')}
          </gml:identifier>
          <ad:inspireId>
          <base:Identifier>
            <base:localId>{fme:get-attribute('identificatie')}</base:localId>
            <base:namespace>NL.KAD.BAG.Address</base:namespace>
            <base:versionId xsi:nil="true" nilReason="other:unpopulated"></base:versionId>
          </base:Identifier>
          </ad:inspireId>
        <ad:alternativeIdentifier xsi:nil="true" nilReason="other:unpopulated"></ad:alternativeIdentifier>
        <ad:position>
          <ad:GeographicPosition>
            <ad:geometry>
              <gml:Point srsName="urn:ogc:def:crs:EPSG::4258" srsDimension="2" gml:id="NL.KAD.BAG.Address.{fme:get-attribute('identificatie')}_P">
               <gml:pos>{fme:get-attribute('_y')} {fme:get-attribute('_x')}</gml:pos>
             </gml:Point>
            </ad:geometry>
            <ad:specification>entrance</ad:specification>
            <ad:method>byOtherParty</ad:method>
            <ad:default>true</ad:default>
          </ad:GeographicPosition>
        </ad:position>
        <ad:locator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisnummer')}</gn:text>
                         <gn:script>Latn</gn:script>
                      </gn:SpellingOfName>
                    </gn:spelling>
                  </gn:GeographicalName>
                </ad:name>
                <ad:type>2</ad:type>
              </ad:LocatorName>
            </ad:name>
            <ad:level>1</ad:level>
          </ad:AddressLocator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisletter')}</gn:text>
                         <gn:script>Latn</gn:script>
                      </gn:SpellingOfName>
                    </gn:spelling>
                  </gn:GeographicalName>
                </ad:name>
                <ad:type>3</ad:type>
              </ad:LocatorName>
            </ad:name>
            <ad:level>1</ad:level>
          </ad:AddressLocator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisnummertoevoeging')}</gn:text>
                         <gn:script>Latn</gn:script>
                      </gn:SpellingOfName>
                    </gn:spelling>
                  </gn:GeographicalName>
                </ad:name>
                <ad:type>4</ad:type>
              </ad:LocatorName>
            </ad:name>
            <ad:level>1</ad:level>
          </ad:AddressLocator>
        </ad:locator>
        <ad:validFrom>{fme:get-attribute('begindatumtijdvakgeldigheid')}</ad:validFrom>
        <ad:validTo>{fme:get-attribute('einddatumtijdvakgeldigheid')}</ad:validTo>
        <ad:beginLifespanVersion xsi:nil="true" nilReason="other:unpopulated"></ad:beginLifespanVersion>
        <ad:endLifespanVersion xsi:nil="true" nilReason="other:unpopulated"></ad:endLifespanVersion>
        <ad:component xmlns:xlink="http://www.w3.org/1999/xlink"
                       xlink:href="#NL.KAD.BAG.AD.ThoroughfareName.{fme:get-attribute('gerelateerdeopenbareruimte')}"/>
        <ad:component xmlns:xlink="http://www.w3.org/1999/xlink" xlink:href="#NL.KAD.BAG.AD.AddressAreaName.{fme:get-attribute('gerelateerdewoonplaats')}"/>
        <ad:component xmlns:xlink="http://www.w3.org/1999/xlink"
                       xlink:href="#NL.KAD.BAG.AD.PostalDescriptor.{fme:get-attribute('postcode')}"/>
      </ad:Address>
      </base:member>
      </base:SpatialDataSet>
    RESULT_ATTRIBUTE = ADRESMEMBER
    -> AttributeCreator
XMLTemplater_4
    OUTPUT_XML_HEADER = No
    VISIBLE_QUERY_VALIDATE = No
    ROOT_QUERY_EXPR:
      <?xml version="1.0" encoding="UTF-8"?>
      <base:SpatialDataSet xmlns:base="urn:x-inspire:specification:gmlas:BaseTypes:3.2"
                           xmlns:ad="urn:x-inspire:specification:gmlas:Addresses:3.0"
                           xmlns:gn="urn:x-inspire:specification:gmlas:GeographicalNames:3.0"
                           xmlns:xlink="http://www.w3.org/1999/xlink"
                           xmlns:xsi="http://www.w3.org/2001/XMLSchema-instance"
                           xmlns:gml="http://www.opengis.net/gml/3.2"
                           xsi:schemaLocation="urn:x-inspire:specification:gmlas:BaseTypes:3.2 http://inspire.ec.europa.eu/schemas/base/3.2/BaseTypes.xsd
                           urn:x-inspire:specification:gmlas:Addresses:3.0 http://inspire.ec.europa.eu/schemas/ad/3.0/Addresses.xsd
                           urn:x-inspire:specification:gmlas:GeographicalNames:3.0 http://inspire.ec.europa.eu/schemas/gn/3.0/GeographicalNames.xsd"
                           gml:id="NL.KAD.BAG.AD">
          <base:identifier>
              <base:Identifier>
                  <base:localId>0</base:localId>
                  <base:namespace>NL.KAD.BAG.AD</base:namespace>
              </base:Identifier>
          </base:identifier>
          <base:metadata xsi:nil="true"/>
      <base:member>
      <ad:Address gml:id="NL.KAD.BAG.Address.{fme:get-attribute('identificatie')}">
          <gml:identifier codeSpace="http://inspire.jrc.ec.europa.eu/">
               urn:x-inspire:object:id:NL.KAD.BAG.AD.Address.{fme:get-attribute('identificatie')}
          </gml:identifier>
          <ad:inspireId>
          <base:Identifier>
            <base:localId>{fme:get-attribute('identificatie')}</base:localId>
            <base:namespace>NL.KAD.BAG.Address</base:namespace>
            <base:versionId xsi:nil="true" nilReason="other:unpopulated"></base:versionId>
          </base:Identifier>
          </ad:inspireId>
        <ad:alternativeIdentifier xsi:nil="true" nilReason="other:unpopulated"></ad:alternativeIdentifier>
        <ad:position>
          <ad:GeographicPosition>
            <ad:geometry>
              <gml:Point srsName="urn:ogc:def:crs:EPSG::4258" srsDimension="2" gml:id="NL.KAD.BAG.Address.{fme:get-attribute('identificatie')}_P">
               <gml:pos>{fme:get-attribute('_y')} {fme:get-attribute('_x')}</gml:pos>
             </gml:Point>
            </ad:geometry>
            <ad:specification>entrance</ad:specification>
            <ad:method>byOtherParty</ad:method>
            <ad:default>true</ad:default>
          </ad:GeographicPosition>
        </ad:position>
        <ad:locator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisnummer')}</gn:text>
                         <gn:script>Latn</gn:script>
                      </gn:SpellingOfName>
                    </gn:spelling>
                  </gn:GeographicalName>
                </ad:name>
                <ad:type>2</ad:type>
              </ad:LocatorName>
            </ad:name>
            <ad:level>1</ad:level>
          </ad:AddressLocator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisletter')}</gn:text>
                         <gn:script>Latn</gn:script>
                      </gn:SpellingOfName>
                    </gn:spelling>
                  </gn:GeographicalName>
                </ad:name>
                <ad:type>3</ad:type>
              </ad:LocatorName>
            </ad:name>
            <ad:level>1</ad:level>
          </ad:AddressLocator>
        </ad:locator>
        <ad:validFrom>{fme:get-attribute('begindatumtijdvakgeldigheid')}</ad:validFrom>
        <ad:validTo>{fme:get-attribute('einddatumtijdvakgeldigheid')}</ad:validTo>
        <ad:beginLifespanVersion xsi:nil="true" nilReason="other:unpopulated"></ad:beginLifespanVersion>
        <ad:endLifespanVersion xsi:nil="true" nilReason="other:unpopulated"></ad:endLifespanVersion>
        <ad:component xmlns:xlink="http://www.w3.org/1999/xlink"
                       xlink:href="#NL.KAD.BAG.AD.ThoroughfareName.{fme:get-attribute('gerelateerdeopenbareruimte')}"/>
        <ad:component xmlns:xlink="http://www.w3.org/1999/xlink" xlink:href="#NL.KAD.BAG.AD.AddressAreaName.{fme:get-attribute('gerelateerdewoonplaats')}"/>
        <ad:component xmlns:xlink="http://www.w3.org/1999/xlink"
                       xlink:href="#NL.KAD.BAG.AD.PostalDescriptor.{fme:get-attribute('postcode')}"/>
      </ad:Address>
      </base:member>
      </base:SpatialDataSet>
    RESULT_ATTRIBUTE = ADRESMEMBER
    -> AttributeCreator
XMLTemplater_5
    OUTPUT_XML_HEADER = No
    VISIBLE_QUERY_VALIDATE = No
    ROOT_QUERY_EXPR:
      <?xml version="1.0" encoding="UTF-8"?>
      <base:SpatialDataSet xmlns:base="urn:x-inspire:specification:gmlas:BaseTypes:3.2"
                           xmlns:ad="urn:x-inspire:specification:gmlas:Addresses:3.0"
                           xmlns:gn="urn:x-inspire:specification:gmlas:GeographicalNames:3.0"
                           xmlns:xlink="http://www.w3.org/1999/xlink"
                           xmlns:xsi="http://www.w3.org/2001/XMLSchema-instance"
                           xmlns:gml="http://www.opengis.net/gml/3.2"
                           xsi:schemaLocation="urn:x-inspire:specification:gmlas:BaseTypes:3.2 http://inspire.ec.europa.eu/schemas/base/3.2/BaseTypes.xsd
                           urn:x-inspire:specification:gmlas:Addresses:3.0 http://inspire.ec.europa.eu/schemas/ad/3.0/Addresses.xsd
                           urn:x-inspire:specification:gmlas:GeographicalNames:3.0 http://inspire.ec.europa.eu/schemas/gn/3.0/GeographicalNames.xsd"
                           gml:id="NL.KAD.BAG.AD">
          <base:identifier>
              <base:Identifier>
                  <base:localId>0</base:localId>
                  <base:namespace>NL.KAD.BAG.AD</base:namespace>
              </base:Identifier>
          </base:identifier>
          <base:metadata xsi:nil="true"/>
      <base:member>
      <ad:Address gml:id="NL.KAD.BAG.Address.{fme:get-attribute('identificatie')}">
          <gml:identifier codeSpace="http://inspire.jrc.ec.europa.eu/">
               urn:x-inspire:object:id:NL.KAD.BAG.AD.Address.{fme:get-attribute('identificatie')}
          </gml:identifier>
          <ad:inspireId>
          <base:Identifier>
            <base:localId>{fme:get-attribute('identificatie')}</base:localId>
            <base:namespace>NL.KAD.BAG.Address</base:namespace>
            <base:versionId xsi:nil="true" nilReason="other:unpopulated"></base:versionId>
          </base:Identifier>
          </ad:inspireId>
        <ad:alternativeIdentifier xsi:nil="true" nilReason="other:unpopulated"></ad:alternativeIdentifier>
        <ad:position>
          <ad:GeographicPosition>
            <ad:geometry>
              <gml:Point srsName="urn:ogc:def:crs:EPSG::4258" srsDimension="2" gml:id="NL.KAD.BAG.Address.{fme:get-attribute('identificatie')}_P">
               <gml:pos>{fme:get-attribute('_y')} {fme:get-attribute('_x')}</gml:pos>
             </gml:Point>
            </ad:geometry>
            <ad:specification>entrance</ad:specification>
            <ad:method>byOtherParty</ad:method>
            <ad:default>true</ad:default>
          </ad:GeographicPosition>
        </ad:position>
        <ad:locator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisnummer')}</gn:text>
                         <gn:script>Latn</gn:script>
                      </gn:SpellingOfName>
                    </gn:spelling>
                  </gn:GeographicalName>
                </ad:name>
                <ad:type>2</ad:type>
              </ad:LocatorName>
            </ad:name>
            <ad:level>1</ad:level>
          </ad:AddressLocator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisnummertoevoeging')}</gn:text>
                         <gn:script>Latn</gn:script>
                      </gn:SpellingOfName>
                    </gn:spelling>
                  </gn:GeographicalName>
                </ad:name>
                <ad:type>4</ad:type>
              </ad:LocatorName>
            </ad:name>
            <ad:level>1</ad:level>
          </ad:AddressLocator>
        </ad:locator>
        <ad:validFrom>{fme:get-attribute('begindatumtijdvakgeldigheid')}</ad:validFrom>
        <ad:validTo>{fme:get-attribute('einddatumtijdvakgeldigheid')}</ad:validTo>
        <ad:beginLifespanVersion xsi:nil="true" nilReason="other:unpopulated"></ad:beginLifespanVersion>
        <ad:endLifespanVersion xsi:nil="true" nilReason="other:unpopulated"></ad:endLifespanVersion>
        <ad:component xmlns:xlink="http://www.w3.org/1999/xlink"
                       xlink:href="#NL.KAD.BAG.AD.ThoroughfareName.{fme:get-attribute('gerelateerdeopenbareruimte')}"/>
        <ad:component xmlns:xlink="http://www.w3.org/1999/xlink" xlink:href="#NL.KAD.BAG.AD.AddressAreaName.{fme:get-attribute('gerelateerdewoonplaats')}"/>
        <ad:component xmlns:xlink="http://www.w3.org/1999/xlink"
                       xlink:href="#NL.KAD.BAG.AD.PostalDescriptor.{fme:get-attribute('postcode')}"/>
      </ad:Address>
      </base:member>
      </base:SpatialDataSet>
    RESULT_ATTRIBUTE = ADRESMEMBER
    -> AttributeCreator
XMLTemplater_6
    OUTPUT_XML_HEADER = No
    VISIBLE_QUERY_VALIDATE = No
    ROOT_QUERY_EXPR:
      <?xml version="1.0" encoding="UTF-8"?>
      <base:SpatialDataSet xmlns:base="urn:x-inspire:specification:gmlas:BaseTypes:3.2"
                           xmlns:ad="urn:x-inspire:specification:gmlas:Addresses:3.0"
                           xmlns:gn="urn:x-inspire:specification:gmlas:GeographicalNames:3.0"
                           xmlns:xlink="http://www.w3.org/1999/xlink"
                           xmlns:xsi="http://www.w3.org/2001/XMLSchema-instance"
                           xmlns:gml="http://www.opengis.net/gml/3.2"
                           xsi:schemaLocation="urn:x-inspire:specification:gmlas:BaseTypes:3.2 http://inspire.ec.europa.eu/schemas/base/3.2/BaseTypes.xsd
                           urn:x-inspire:specification:gmlas:Addresses:3.0 http://inspire.ec.europa.eu/schemas/ad/3.0/Addresses.xsd
                           urn:x-inspire:specification:gmlas:GeographicalNames:3.0 http://inspire.ec.europa.eu/schemas/gn/3.0/GeographicalNames.xsd"
                           gml:id="NL.KAD.BAG.AD">
          <base:identifier>
              <base:Identifier>
                  <base:localId>0</base:localId>
                  <base:namespace>NL.KAD.BAG.AD</base:namespace>
              </base:Identifier>
          </base:identifier>
          <base:metadata xsi:nil="true"/>
      <base:member>
      <ad:Address gml:id="NL.KAD.BAG.Address.{fme:get-attribute('identificatie')}">
          <gml:identifier codeSpace="http://inspire.jrc.ec.europa.eu/">
               urn:x-inspire:object:id:NL.KAD.BAG.AD.Address.{fme:get-attribute('identificatie')}
          </gml:identifier>
          <ad:inspireId>
          <base:Identifier>
            <base:localId>{fme:get-attribute('identificatie')}</base:localId>
            <base:namespace>NL.KAD.BAG.Address</base:namespace>
            <base:versionId xsi:nil="true" nilReason="other:unpopulated"></base:versionId>
          </base:Identifier>
          </ad:inspireId>
        <ad:alternativeIdentifier xsi:nil="true" nilReason="other:unpopulated"></ad:alternativeIdentifier>
        <ad:position>
          <ad:GeographicPosition>
            <ad:geometry>
              <gml:Point srsName="urn:ogc:def:crs:EPSG::4258" srsDimension="2" gml:id="NL.KAD.BAG.Address.{fme:get-attribute('identificatie')}_P">
               <gml:pos>{fme:get-attribute('_y')} {fme:get-attribute('_x')}</gml:pos>
             </gml:Point>
            </ad:geometry>
            <ad:specification>entrance</ad:specification>
            <ad:method>byOtherParty</ad:method>
            <ad:default>true</ad:default>
          </ad:GeographicPosition>
        </ad:position>
        <ad:locator>
          <ad:AddressLocator>
            <ad:name>
              <ad:LocatorName>
                <ad:name>
                  <gn:GeographicalName>
                    <gn:language>NL</gn:language>
                    <gn:nativeness>endonym</gn:nativeness>
                    <gn:nameStatus  nilReason="other:unpopulated" xsi:nil="true"></gn:nameStatus>
                    <gn:sourceOfName xsi:nil="true" nilReason="other:unpopulated"></gn:sourceOfName>
                    <gn:pronunciation nilReason="other:unpopulated" xsi:nil="true"/>
                    <gn:spelling>
                      <gn:SpellingOfName>
                        <gn:text>{fme:get-attribute('huisnummer')}</gn:text>
                         <gn:script>Latn</gn:script>
                      </gn:SpellingOfName>
                    </gn:spelling>
                  </gn:GeographicalName>
                </ad:name>
                <ad:type>2</ad:type>
              </ad:LocatorName>
            </ad:name>
            <ad:level>1</ad:level>
          </ad:AddressLocator>
        </ad:locator>
        <ad:validFrom>{fme:get-attribute('begindatumtijdvakgeldigheid')}</ad:validFrom>
        <ad:validTo>{fme:get-attribute('einddatumtijdvakgeldigheid')}</ad:validTo>
        <ad:beginLifespanVersion xsi:nil="true" nilReason="other:unpopulated"></ad:beginLifespanVersion>
        <ad:endLifespanVersion xsi:nil="true" nilReason="other:unpopulated"></ad:endLifespanVersion>
        <ad:component xmlns:xlink="http://www.w3.org/1999/xlink"
                       xlink:href="#NL.KAD.BAG.AD.ThoroughfareName.{fme:get-attribute('gerelateerdeopenbareruimte')}"/>
        <ad:component xmlns:xlink="http://www.w3.org/1999/xlink" xlink:href="#NL.KAD.BAG.AD.AddressAreaName.{fme:get-attribute('gerelateerdewoonplaats')}"/>
        <ad:component xmlns:xlink="http://www.w3.org/1999/xlink"
                       xlink:href="#NL.KAD.BAG.AD.PostalDescriptor.{fme:get-attribute('postcode')}"/>
      </ad:Address>
      </base:member>
      </base:SpatialDataSet>
    RESULT_ATTRIBUTE = ADRESMEMBER
    -> AttributeCreator
AttributeCreator
    ATTR_LIST = ft_type,12
    -> AttributeExpressionRemover
AttributeExpressionRemover
    ATTR_EXP = postgis*
    -> 2DForcer
2DForcer
    2D -> AttributeCopier
AttributeCopier
    ATTR_LIST = gml_id,identificatie,binary_object,ADRESMEMBER
    -> StringConcatenator
StringConcatenator
    PARM_LINE = fme_basicstring:19%14:NL.KAD.BAG.Address.@Value(gml_id)
    VAL_ATTR = gml_id
    -> BinaryEncoder
BinaryEncoder
    DEST_ATTR = binary_object
    ENCODING_TYPE = HEX
    ATTR_TO_ENCODE = binary_object
    -> inspire_ad_blob.gml_objects (writer POSTGIS_2)
inspire_ad_blob.gml_objects (writer POSTGIS_2)
    attributes: id serial,PRIKEY, gml_id text,none, ft_type int2, binary_object bytea
