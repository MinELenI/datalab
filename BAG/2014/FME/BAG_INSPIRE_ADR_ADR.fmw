FME workspace BAG_INSPIRE_ADR_ADR.fmw
Title: Inspire adressen
Description: Workspace voor INSPIRE adressen
History: 7-2-13,EJBodewitz,Aanpassing voor QGis

Parameters:
- LOG_FILE = $(FME_MF_DIR)test10.log   # Log File
- MAX_FEATURES = 10   # Max Features to Read
- DestDataset_INSPIRE = D:\Projects\PDOK\BAG\2014\XML\Adressen.xml   # Destination Geography Markup Language (GML) File

Readers:
- POSTGIS_1: POSTGIS from pdok

Writers:
- INSPIRE_1: INSPIRE to $(DestDataset_INSPIRE)

DuplicateRemover
    KEYATTR = postcode
    UNIQUE -> AttributeCreator_2
AttributeCreator_2
    ATTR_LIST = gml_identifier,@Value(postcode),inspireId.Identifier.localId,@Value(postcode),postCode,@Value(postcode)
    -> GeometryRemover
GeometryRemover
    -> PostalDescriptor (writer INSPIRE_1)
DuplicateRemover_2
    KEYATTR = gerelateerdeopenbareruimte
    UNIQUE -> AttributeCreator_3
AttributeCreator_3
    ATTR_LIST = gml_identifier,@Value(gerelateerdeopenbareruimte),inspireId.Identifier.localId,@Value(gerelateerdeopenbareruimte),name{0}.GeographicalName.spelling{0}.SpellingOfName.text,@Value(openbareruimtenaam),name{0}.GeographicalName.language,NL,inspireId.Identifier.namespace,NL.KAD.BAG.ThoroughfareName,name{0}.GeographicalName.nativeness,endonym,name{0}.GeographicalName.spelling{0}.SpellingOfName.text,@Value(openbareruimtenaam),name{0}.GeographicalName.spelling{0}.SpellingOfName.script,Latn,name{0}.GeographicalName.sourceOfName,Kadaster
    -> GeometryRemover_2
GeometryRemover_2
    -> ThoroughfareName (writer INSPIRE_1)
DuplicateRemover_3
    KEYATTR = gerelateerdewoonplaats
    UNIQUE -> AttributeCreator_4
AttributeCreator_4
    ATTR_LIST = gml_identifier,@Value(gerelateerdewoonplaats),inspireId.Identifier.localId,@Value(gerelateerdewoonplaats),name{0}.GeographicalName.spelling{0}.SpellingOfName.text,@Value(woonplaatsnaam),name{0}.GeographicalName.language,NL,inspireId.Identifier.namespace,NL.KAD.BAG.AddressAreaName,name{0}.GeographicalName.nativeness,endonym,name{0}.GeographicalName.spelling{0}.SpellingOfName.text,@Value(woonplaatsnaam),name{0}.GeographicalName.spelling{0}.SpellingOfName.script,Latn,name{0}.GeographicalName.sourceOfName,Kadaster
    -> GeometryRemover_3
GeometryRemover_3
    -> AddressAreaName (writer INSPIRE_1)

Bookmark: postgis data lig- en standplaats
bag.standplaats (reader POSTGIS_1)
    attributes: gid serial,PRIKEY, identificatie float8,BTREE, aanduidingrecordinactief bool, aanduidingrecordcorrectie int4, officieel bool, inonderzoek bool, begindatumtijdvakgeldigheid timestamp, einddatumtijdvakgeldigheid timestamp, documentnummer varchar(20), documentdatum date, hoofdadres float8, standplaatsstatus char(4), geom_valid bool
    -> CenterPointReplacer
    -> DuplicateRemover
    -> DuplicateRemover_2
    -> DuplicateRemover_3
bag.ligplaats (reader POSTGIS_1) [off]
    attributes: gid serial,PRIKEY, identificatie float8,BTREE, aanduidingrecordinactief bool, aanduidingrecordcorrectie int4, officieel bool, inonderzoek bool, begindatumtijdvakgeldigheid timestamp, einddatumtijdvakgeldigheid timestamp, documentnummer varchar(20), documentdatum date, hoofdadres float8, ligplaatsstatus char(4), geom_valid bool
    -> CenterPointReplacer
    -> DuplicateRemover
    -> DuplicateRemover_2
    -> DuplicateRemover_3
CenterPointReplacer
    CENTERPOINT -> CsmapReprojector_2

Bookmark: postgis data verblijfsobject en nummeraanduiding
bag.verblijfsobject (reader POSTGIS_1) [off]
    attributes: gid serial,PRIKEY, identificatie float8,BTREE, begindatumtijdvakgeldigheid timestamp, einddatumtijdvakgeldigheid timestamp, gerelateerdeopenbareruimte float8, openbareruimtenaam varchar(80), gerelateerdewoonplaats float8, woonplaatsnaam varchar(80), huisnummer float8, huisletter varchar(1), huisnummertoevoeging varchar(4), nummeraanduidingstatus varchar(4), postcode varchar(6)
    -> CsmapReprojector_2
    -> DuplicateRemover
    -> DuplicateRemover_2
    -> DuplicateRemover_3

Bookmark: Verwerking adressen
CsmapReprojector_2
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> DateFormatter
DateFormatter
    DATE_ATTR = begindatumtijdvakgeldigheid,einddatumtijdvakgeldigheid
    FMT = %Y-%m-%dT00:00:00
    -> 2DForcer
2DForcer
    2D -> AttributeCreator
AttributeCreator
    ATTR_LIST = gml_id,@Value(identificatie),gml_identifier,@Value(identificatie),inspireId.Identifier.localId,@Value(identificatie),inspireId.Identifier.namespace,NL.KAD.BAG.AD.Address,validFrom,@Value(begindatumtijdvakgeldigheid),validTo,@Value(einddatumtijdvakgeldigheid),beginLifespanVersion,@Value(begindatumtijdvakgeldigheid),endLifespanVersion,@Value(einddatumtijdvakgeldigheid),component{0}.xlink_href,#NL.KAD.BAG.AD.ThoroughfareName.@Value(gerelateerdeopenbareruimte),component{1}.xlink_href,#NL.KAD.BAG.AD.AddressAreaName.@Value(gerelateerdewoonplaats),component{2}.xlink_href,#NL.KAD.BAG.AD.PostalDescriptor.@Value(postcode)
    -> Tester
GeometryPropertySetter
    OVERWRITE_CHOICE = Yes
    SETTYPE_PARAM = Geometry Name
    GEOM_NAME_FIELD = position{0}.GeographicPosition.geometry
    SET -> Address (writer INSPIRE_1)

Bookmark: Huisnummer, Huisletter, Huisnummertoevoeging
Tester
    TEST_MODE = Automatic
    TEST_DESCRIPTION = ""
    BOOL_OP = OR
    TEST_CLAUSE = TEST huisnummer NOT_ATTRIBUTE_VALUE_NULL ""
    PASSED -> AttributeCopier
    FAILED -> Tester_2
AttributeCopier
    ATTR_LIST = huisnummer,locator{0}.AddressLocator.designator{0}.LocatorDesignator.designator,"","",locator{0}.AddressLocator.designator{0}.LocatorDesignator.type,2
    -> Tester_2
Tester_2
    TEST_MODE = Automatic
    TEST_DESCRIPTION = ""
    BOOL_OP = OR
    TEST_CLAUSE = TEST huisletter NOT_ATTRIBUTE_VALUE_NULL ""
    PASSED -> AttributeCopier_2
    FAILED -> Tester_3
AttributeCopier_2
    ATTR_LIST = huisletter,locator{0}.AddressLocator.designator{1}.LocatorDesignator.designator,"","",locator{0}.AddressLocator.designator{1}.LocatorDesignator.type,3
    -> Tester_3
Tester_3
    TEST_MODE = Automatic
    TEST_DESCRIPTION = ""
    BOOL_OP = OR
    TEST_CLAUSE = TEST huisnummertoevoeging NOT_ATTRIBUTE_VALUE_NULL ""
    PASSED -> AttributeCopier_3
    FAILED -> GeometryPropertySetter
AttributeCopier_3
    ATTR_LIST = huisnummertoevoeging,locator{0}.AddressLocator.designator{2}.LocatorDesignator.designator,"","",locator{0}.AddressLocator.designator{2}.LocatorDesignator.type,4
    -> GeometryPropertySetter

Bookmark: INSPIRE uitvoer GML
Address (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, inspireId.Identifier.localId xml_buffer, inspireId.Identifier.namespace xml_buffer, inspireId.Identifier.versionId xml_buffer, inspireId.Identifier.versionId.nilReason xml_buffer, inspireId.Identifier.versionId.xsi_nil xml_boolean, alternativeIdentifier xml_buffer, alternativeIdentifier.nilReason xml_buffer, alternativeIdentifier.xsi_nil xml_boolean, position{}.GeographicPosition.geometry xml_geometry,
      position{}.GeographicPosition.specification xml_buffer, position{}.GeographicPosition.specification.nilReason xml_buffer, position{}.GeographicPosition.specification.codeSpace xml_buffer, position{}.GeographicPosition.specification.xsi_nil xml_boolean, position{}.GeographicPosition.method xml_buffer, position{}.GeographicPosition.method.nilReason xml_buffer, position{}.GeographicPosition.method.codeSpace xml_buffer, position{}.GeographicPosition.method.xsi_nil xml_boolean, position{}.GeographicPosition.default xml_boolean, status xml_buffer, status.nilReason xml_buffer, status.codeSpace xml_buffer, status.xsi_nil xml_boolean, locator{}.AddressLocator.designator{}.LocatorDesignator.designator xml_buffer, locator{}.AddressLocator.designator{}.LocatorDesignator.type xml_buffer, locator{}.AddressLocator.designator{}.LocatorDesignator.type.codeSpace xml_buffer, locator{}.AddressLocator.name{}.LocatorName.name{}.GeographicalName.language xml_buffer, locator{}.AddressLocator.name{}.LocatorName.name{}.GeographicalName.language.nilReason xml_buffer, locator{}.AddressLocator.name{}.LocatorName.name{}.GeographicalName.language.xsi_nil xml_boolean, locator{}.AddressLocator.name{}.LocatorName.name{}.GeographicalName.nativeness xml_buffer, locator{}.AddressLocator.name{}.LocatorName.name{}.GeographicalName.nativeness.nilReason xml_buffer, locator{}.AddressLocator.name{}.LocatorName.name{}.GeographicalName.nativeness.codeSpace xml_buffer, locator{}.AddressLocator.name{}.LocatorName.name{}.GeographicalName.nativeness.xsi_nil xml_boolean, locator{}.AddressLocator.name{}.LocatorName.name{}.GeographicalName.nameStatus xml_buffer, locator{}.AddressLocator.name{}.LocatorName.name{}.GeographicalName.nameStatus.nilReason xml_buffer, locator{}.AddressLocator.name{}.LocatorName.name{}.GeographicalName.nameStatus.codeSpace xml_buffer, locator{}.AddressLocator.name{}.LocatorName.name{}.GeographicalName.nameStatus.xsi_nil xml_boolean, locator{}.AddressLocator.name{}.LocatorName.name{}.GeographicalName.sourceOfName xml_buffer, locator{}.AddressLocator.name{}.LocatorName.name{}.GeographicalName.sourceOfName.nilReason xml_buffer, locator{}.AddressLocator.name{}.LocatorName.name{}.GeographicalName.sourceOfName.xsi_nil xml_boolean,
      locator{}.AddressLocator.name{}.LocatorName.name{}.GeographicalName.pronunciation.nilReason xml_buffer, locator{}.AddressLocator.name{}.LocatorName.name{}.GeographicalName.pronunciation.xsi_nil xml_boolean, locator{}.AddressLocator.name{}.LocatorName.name{}.GeographicalName.pronunciation.PronunciationOfName.pronunciationSoundLink xml_buffer, locator{}.AddressLocator.name{}.LocatorName.name{}.GeographicalName.pronunciation.PronunciationOfName.pronunciationSoundLink.nilReason xml_buffer, locator{}.AddressLocator.name{}.LocatorName.name{}.GeographicalName.pronunciation.PronunciationOfName.pronunciationSoundLink.xsi_nil xml_boolean, locator{}.AddressLocator.name{}.LocatorName.name{}.GeographicalName.pronunciation.PronunciationOfName.pronunciationIPA xml_buffer, locator{}.AddressLocator.name{}.LocatorName.name{}.GeographicalName.pronunciation.PronunciationOfName.pronunciationIPA.nilReason xml_buffer, locator{}.AddressLocator.name{}.LocatorName.name{}.GeographicalName.pronunciation.PronunciationOfName.pronunciationIPA.xsi_nil xml_boolean, locator{}.AddressLocator.name{}.LocatorName.name{}.GeographicalName.spelling{}.SpellingOfName.text xml_buffer, locator{}.AddressLocator.name{}.LocatorName.name{}.GeographicalName.spelling{}.SpellingOfName.script xml_buffer, locator{}.AddressLocator.name{}.LocatorName.name{}.GeographicalName.spelling{}.SpellingOfName.script.nilReason xml_buffer, locator{}.AddressLocator.name{}.LocatorName.name{}.GeographicalName.spelling{}.SpellingOfName.script.xsi_nil xml_boolean, locator{}.AddressLocator.name{}.LocatorName.name{}.GeographicalName.spelling{}.SpellingOfName.transliterationScheme xml_buffer, locator{}.AddressLocator.name{}.LocatorName.name{}.GeographicalName.spelling{}.SpellingOfName.transliterationScheme.nilReason xml_buffer, locator{}.AddressLocator.name{}.LocatorName.name{}.GeographicalName.spelling{}.SpellingOfName.transliterationScheme.xsi_nil xml_boolean, locator{}.AddressLocator.name{}.LocatorName.name{}.GeographicalName.grammaticalGender xml_buffer, locator{}.AddressLocator.name{}.LocatorName.name{}.GeographicalName.grammaticalGender.nilReason xml_buffer, locator{}.AddressLocator.name{}.LocatorName.name{}.GeographicalName.grammaticalGender.codeSpace xml_buffer, locator{}.AddressLocator.name{}.LocatorName.name{}.GeographicalName.grammaticalGender.xsi_nil xml_boolean, locator{}.AddressLocator.name{}.LocatorName.name{}.GeographicalName.grammaticalNumber xml_buffer, locator{}.AddressLocator.name{}.LocatorName.name{}.GeographicalName.grammaticalNumber.nilReason xml_buffer, locator{}.AddressLocator.name{}.LocatorName.name{}.GeographicalName.grammaticalNumber.codeSpace xml_buffer, locator{}.AddressLocator.name{}.LocatorName.name{}.GeographicalName.grammaticalNumber.xsi_nil xml_boolean, locator{}.AddressLocator.name{}.LocatorName.type xml_buffer, locator{}.AddressLocator.name{}.LocatorName.type.codeSpace xml_buffer, locator{}.AddressLocator.level xml_buffer, locator{}.AddressLocator.level.codeSpace xml_buffer, locator{}.AddressLocator.withinScopeOf.owns xml_boolean, locator{}.AddressLocator.withinScopeOf.nilReason xml_buffer, locator{}.AddressLocator.withinScopeOf.gml_remoteSchema xml_buffer,
      locator{}.AddressLocator.withinScopeOf.xlink_href xml_buffer, locator{}.AddressLocator.withinScopeOf.xsi_nil xml_boolean, validFrom xml_datetime, validFrom.nilReason xml_buffer, validFrom.xsi_nil xml_boolean, validTo xml_datetime, validTo.nilReason xml_buffer, validTo.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, parcel{}.owns xml_boolean, parcel{}.nilReason xml_buffer, parcel{}.gml_remoteSchema xml_buffer, parcel{}.xlink_href xml_buffer, parcel{}.xsi_nil xml_boolean, parentAddress.owns xml_boolean, parentAddress.nilReason xml_buffer, parentAddress.gml_remoteSchema xml_buffer, parentAddress.xlink_href xml_buffer, parentAddress.xsi_nil xml_boolean, building{}.owns xml_boolean, building{}.nilReason xml_buffer, building{}.gml_remoteSchema xml_buffer, building{}.xlink_href xml_buffer, building{}.xsi_nil xml_boolean, component{}.nilReason xml_buffer,
      component{}.gml_remoteSchema xml_buffer, component{}.xlink_href xml_buffer, component{}.owns xml_boolean
PostalDescriptor (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, inspireId.Identifier.localId xml_buffer, inspireId.Identifier.namespace xml_buffer, inspireId.Identifier.versionId xml_buffer, inspireId.Identifier.versionId.nilReason xml_buffer, inspireId.Identifier.versionId.xsi_nil xml_boolean, alternativeIdentifier xml_buffer, alternativeIdentifier.nilReason xml_buffer, alternativeIdentifier.xsi_nil xml_boolean, beginLifespanVersion xml_datetime,
      beginLifespanVersion.nilReason xml_buffer, beginLifespanVersion.xsi_nil xml_boolean, endLifespanVersion xml_datetime, endLifespanVersion.nilReason xml_buffer, endLifespanVersion.xsi_nil xml_boolean, status xml_buffer, status.nilReason xml_buffer, status.codeSpace xml_buffer, status.xsi_nil xml_boolean, validFrom xml_datetime, validFrom.nilReason xml_buffer, validFrom.xsi_nil xml_boolean, validTo xml_datetime, validTo.nilReason xml_buffer, validTo.xsi_nil xml_boolean, situatedWithin{}.owns xml_boolean, situatedWithin{}.nilReason xml_buffer, situatedWithin{}.gml_remoteSchema xml_buffer, situatedWithin{}.xlink_href xml_buffer, situatedWithin{}.xsi_nil xml_boolean, postName{}.GeographicalName.language xml_buffer, postName{}.GeographicalName.language.nilReason xml_buffer, postName{}.GeographicalName.language.xsi_nil xml_boolean, postName{}.GeographicalName.nativeness xml_buffer, postName{}.GeographicalName.nativeness.nilReason xml_buffer, postName{}.GeographicalName.nativeness.codeSpace xml_buffer, postName{}.GeographicalName.nativeness.xsi_nil xml_boolean, postName{}.GeographicalName.nameStatus xml_buffer, postName{}.GeographicalName.nameStatus.nilReason xml_buffer, postName{}.GeographicalName.nameStatus.codeSpace xml_buffer,
      postName{}.GeographicalName.nameStatus.xsi_nil xml_boolean, postName{}.GeographicalName.sourceOfName xml_buffer, postName{}.GeographicalName.sourceOfName.nilReason xml_buffer, postName{}.GeographicalName.sourceOfName.xsi_nil xml_boolean, postName{}.GeographicalName.pronunciation.nilReason xml_buffer, postName{}.GeographicalName.pronunciation.xsi_nil xml_boolean, postName{}.GeographicalName.pronunciation.PronunciationOfName.pronunciationSoundLink xml_buffer, postName{}.GeographicalName.pronunciation.PronunciationOfName.pronunciationSoundLink.nilReason xml_buffer, postName{}.GeographicalName.pronunciation.PronunciationOfName.pronunciationSoundLink.xsi_nil xml_boolean, postName{}.GeographicalName.pronunciation.PronunciationOfName.pronunciationIPA xml_buffer, postName{}.GeographicalName.pronunciation.PronunciationOfName.pronunciationIPA.nilReason xml_buffer, postName{}.GeographicalName.pronunciation.PronunciationOfName.pronunciationIPA.xsi_nil xml_boolean, postName{}.GeographicalName.spelling{}.SpellingOfName.text xml_buffer, postName{}.GeographicalName.spelling{}.SpellingOfName.script xml_buffer, postName{}.GeographicalName.spelling{}.SpellingOfName.script.nilReason xml_buffer, postName{}.GeographicalName.spelling{}.SpellingOfName.script.xsi_nil xml_boolean, postName{}.GeographicalName.spelling{}.SpellingOfName.transliterationScheme xml_buffer, postName{}.GeographicalName.spelling{}.SpellingOfName.transliterationScheme.nilReason xml_buffer, postName{}.GeographicalName.spelling{}.SpellingOfName.transliterationScheme.xsi_nil xml_boolean, postName{}.GeographicalName.grammaticalGender xml_buffer, postName{}.GeographicalName.grammaticalGender.nilReason xml_buffer, postName{}.GeographicalName.grammaticalGender.codeSpace xml_buffer, postName{}.GeographicalName.grammaticalGender.xsi_nil xml_boolean, postName{}.GeographicalName.grammaticalNumber xml_buffer, postName{}.GeographicalName.grammaticalNumber.nilReason xml_buffer, postName{}.GeographicalName.grammaticalNumber.codeSpace xml_buffer, postName{}.GeographicalName.grammaticalNumber.xsi_nil xml_boolean, postCode xml_buffer
ThoroughfareName (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, inspireId.Identifier.localId xml_buffer, inspireId.Identifier.namespace xml_buffer, inspireId.Identifier.versionId xml_buffer, inspireId.Identifier.versionId.nilReason xml_buffer, inspireId.Identifier.versionId.xsi_nil xml_boolean, alternativeIdentifier xml_buffer, alternativeIdentifier.nilReason xml_buffer, alternativeIdentifier.xsi_nil xml_boolean, beginLifespanVersion xml_datetime,
      beginLifespanVersion.nilReason xml_buffer, beginLifespanVersion.xsi_nil xml_boolean, endLifespanVersion xml_datetime, endLifespanVersion.nilReason xml_buffer, endLifespanVersion.xsi_nil xml_boolean, status xml_buffer, status.nilReason xml_buffer, status.codeSpace xml_buffer, status.xsi_nil xml_boolean, validFrom xml_datetime, validFrom.nilReason xml_buffer, validFrom.xsi_nil xml_boolean, validTo xml_datetime, validTo.nilReason xml_buffer, validTo.xsi_nil xml_boolean, situatedWithin{}.owns xml_boolean, situatedWithin{}.nilReason xml_buffer, situatedWithin{}.gml_remoteSchema xml_buffer, situatedWithin{}.xlink_href xml_buffer, situatedWithin{}.xsi_nil xml_boolean, name{}.GeographicalName.language xml_buffer, name{}.GeographicalName.language.nilReason xml_buffer, name{}.GeographicalName.language.xsi_nil xml_boolean, name{}.GeographicalName.nativeness xml_buffer, name{}.GeographicalName.nativeness.nilReason xml_buffer, name{}.GeographicalName.nativeness.codeSpace xml_buffer, name{}.GeographicalName.nativeness.xsi_nil xml_boolean, name{}.GeographicalName.nameStatus xml_buffer, name{}.GeographicalName.nameStatus.nilReason xml_buffer, name{}.GeographicalName.nameStatus.codeSpace xml_buffer,
      name{}.GeographicalName.nameStatus.xsi_nil xml_boolean, name{}.GeographicalName.sourceOfName xml_buffer, name{}.GeographicalName.sourceOfName.nilReason xml_buffer, name{}.GeographicalName.sourceOfName.xsi_nil xml_boolean, name{}.GeographicalName.pronunciation.nilReason xml_buffer, name{}.GeographicalName.pronunciation.xsi_nil xml_boolean, name{}.GeographicalName.pronunciation.PronunciationOfName.pronunciationSoundLink xml_buffer, name{}.GeographicalName.pronunciation.PronunciationOfName.pronunciationSoundLink.nilReason xml_buffer, name{}.GeographicalName.pronunciation.PronunciationOfName.pronunciationSoundLink.xsi_nil xml_boolean, name{}.GeographicalName.pronunciation.PronunciationOfName.pronunciationIPA xml_buffer, name{}.GeographicalName.pronunciation.PronunciationOfName.pronunciationIPA.nilReason xml_buffer, name{}.GeographicalName.pronunciation.PronunciationOfName.pronunciationIPA.xsi_nil xml_boolean, name{}.GeographicalName.spelling{}.SpellingOfName.text xml_buffer, name{}.GeographicalName.spelling{}.SpellingOfName.script xml_buffer, name{}.GeographicalName.spelling{}.SpellingOfName.script.nilReason xml_buffer, name{}.GeographicalName.spelling{}.SpellingOfName.script.xsi_nil xml_boolean, name{}.GeographicalName.spelling{}.SpellingOfName.transliterationScheme xml_buffer, name{}.GeographicalName.spelling{}.SpellingOfName.transliterationScheme.nilReason xml_buffer, name{}.GeographicalName.spelling{}.SpellingOfName.transliterationScheme.xsi_nil xml_boolean, name{}.GeographicalName.grammaticalGender xml_buffer, name{}.GeographicalName.grammaticalGender.nilReason xml_buffer, name{}.GeographicalName.grammaticalGender.codeSpace xml_buffer, name{}.GeographicalName.grammaticalGender.xsi_nil xml_boolean, name{}.GeographicalName.grammaticalNumber xml_buffer, name{}.GeographicalName.grammaticalNumber.nilReason xml_buffer, name{}.GeographicalName.grammaticalNumber.codeSpace xml_buffer, name{}.GeographicalName.grammaticalNumber.xsi_nil xml_boolean, transportLink{}.owns xml_boolean, transportLink{}.nilReason xml_buffer, transportLink{}.gml_remoteSchema xml_buffer,
      transportLink{}.xlink_href xml_buffer, transportLink{}.xsi_nil xml_boolean
AddressAreaName (writer INSPIRE_1)
    attributes: gml_parent_id xml_buffer, gml_metaDataProperty{} xml_xml, gml_metaDataProperty{}.about xml_buffer, gml_metaDataProperty{}.nilReason xml_buffer, gml_metaDataProperty{}.gml_remoteSchema xml_buffer, gml_metaDataProperty{}.xlink_href xml_buffer, gml_description xml_buffer, gml_description.nilReason xml_buffer, gml_description.gml_remoteSchema xml_buffer, gml_description.xlink_href xml_buffer, gml_descriptionReference.owns xml_boolean, gml_descriptionReference.nilReason xml_buffer, gml_descriptionReference.gml_remoteSchema xml_buffer, gml_descriptionReference.xlink_href xml_buffer, gml_identifier xml_buffer, gml_identifier.codeSpace xml_buffer, gml_name{} xml_buffer, gml_name{}.codeSpace xml_buffer, gml_boundedBy xml_geometry, gml_location xml_geometry, gml_priorityLocation xml_geometry, inspireId.Identifier.localId xml_buffer, inspireId.Identifier.namespace xml_buffer, inspireId.Identifier.versionId xml_buffer, inspireId.Identifier.versionId.nilReason xml_buffer, inspireId.Identifier.versionId.xsi_nil xml_boolean, alternativeIdentifier xml_buffer, alternativeIdentifier.nilReason xml_buffer, alternativeIdentifier.xsi_nil xml_boolean, beginLifespanVersion xml_datetime,
      beginLifespanVersion.nilReason xml_buffer, beginLifespanVersion.xsi_nil xml_boolean, endLifespanVersion xml_datetime, endLifespanVersion.nilReason xml_buffer, endLifespanVersion.xsi_nil xml_boolean, status xml_buffer, status.nilReason xml_buffer, status.codeSpace xml_buffer, status.xsi_nil xml_boolean, validFrom xml_datetime, validFrom.nilReason xml_buffer, validFrom.xsi_nil xml_boolean, validTo xml_datetime, validTo.nilReason xml_buffer, validTo.xsi_nil xml_boolean, situatedWithin{}.owns xml_boolean, situatedWithin{}.nilReason xml_buffer, situatedWithin{}.gml_remoteSchema xml_buffer, situatedWithin{}.xlink_href xml_buffer, situatedWithin{}.xsi_nil xml_boolean, name{}.GeographicalName.language xml_buffer, name{}.GeographicalName.language.nilReason xml_buffer, name{}.GeographicalName.language.xsi_nil xml_boolean, name{}.GeographicalName.nativeness xml_buffer, name{}.GeographicalName.nativeness.nilReason xml_buffer, name{}.GeographicalName.nativeness.codeSpace xml_buffer, name{}.GeographicalName.nativeness.xsi_nil xml_boolean, name{}.GeographicalName.nameStatus xml_buffer, name{}.GeographicalName.nameStatus.nilReason xml_buffer, name{}.GeographicalName.nameStatus.codeSpace xml_buffer,
      name{}.GeographicalName.nameStatus.xsi_nil xml_boolean, name{}.GeographicalName.sourceOfName xml_buffer, name{}.GeographicalName.sourceOfName.nilReason xml_buffer, name{}.GeographicalName.sourceOfName.xsi_nil xml_boolean, name{}.GeographicalName.pronunciation.nilReason xml_buffer, name{}.GeographicalName.pronunciation.xsi_nil xml_boolean, name{}.GeographicalName.pronunciation.PronunciationOfName.pronunciationSoundLink xml_buffer, name{}.GeographicalName.pronunciation.PronunciationOfName.pronunciationSoundLink.nilReason xml_buffer, name{}.GeographicalName.pronunciation.PronunciationOfName.pronunciationSoundLink.xsi_nil xml_boolean, name{}.GeographicalName.pronunciation.PronunciationOfName.pronunciationIPA xml_buffer, name{}.GeographicalName.pronunciation.PronunciationOfName.pronunciationIPA.nilReason xml_buffer, name{}.GeographicalName.pronunciation.PronunciationOfName.pronunciationIPA.xsi_nil xml_boolean, name{}.GeographicalName.spelling{}.SpellingOfName.text xml_buffer, name{}.GeographicalName.spelling{}.SpellingOfName.script xml_buffer, name{}.GeographicalName.spelling{}.SpellingOfName.script.nilReason xml_buffer, name{}.GeographicalName.spelling{}.SpellingOfName.script.xsi_nil xml_boolean, name{}.GeographicalName.spelling{}.SpellingOfName.transliterationScheme xml_buffer, name{}.GeographicalName.spelling{}.SpellingOfName.transliterationScheme.nilReason xml_buffer, name{}.GeographicalName.spelling{}.SpellingOfName.transliterationScheme.xsi_nil xml_boolean, name{}.GeographicalName.grammaticalGender xml_buffer, name{}.GeographicalName.grammaticalGender.nilReason xml_buffer, name{}.GeographicalName.grammaticalGender.codeSpace xml_buffer, name{}.GeographicalName.grammaticalGender.xsi_nil xml_boolean, name{}.GeographicalName.grammaticalNumber xml_buffer, name{}.GeographicalName.grammaticalNumber.nilReason xml_buffer, name{}.GeographicalName.grammaticalNumber.codeSpace xml_buffer, name{}.GeographicalName.grammaticalNumber.xsi_nil xml_boolean, namedPlace.owns xml_boolean, namedPlace.nilReason xml_buffer, namedPlace.gml_remoteSchema xml_buffer,
      namedPlace.xlink_href xml_buffer, namedPlace.xsi_nil xml_boolean
