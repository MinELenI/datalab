FME workspace Nationaleparken.fmw

Parameters:
- DestDataset_POSTGIS = pdok   # Destination PostGIS Dataset
- SourceDataset_POSTGIS_2 = pdok   # Source PostGIS Dataset

Readers:
- POSTGIS_1: POSTGIS from $(SourceDataset_POSTGIS_2)

Writers:
- POSTGIS_2: POSTGIS to $(DestDataset_POSTGIS)

nationaleparken.nationaleparken_imp (reader POSTGIS_1)
    attributes: gid serial,PRIKEY, naam varchar(50), instrument varchar(20), nr int2, datum date, bron varchar(20), fiat_secr varchar(3), hectares float8, geom_valid bool
    -> Tester
Tester
    TEST_DESCRIPTION = ""
    TEST_CLAUSE = TEST "@Value(instrument)" = "Nationaal Park"
    BOOL_OP = OR
    TEST_MODE = Automatic
    PASSED -> DateFormatter
DateFormatter
    FMT = XML DateTime (%Y-%m-%dT%H:%M:%S)
    DATE_ATTR = datum
    -> Reprojector
Reprojector
    DEST = EPSG:4258
    SOURCE = Read from feature
    RASTER_CELL_SIZE = Preserve Cells
    INTERPOLATION_TYPE_NAME = Nearest Neighbor
    STROKE_ARCS = Yes
    REPROJECTED -> GeometryExtractor
GeometryExtractor
    KIND_LONG = OGC Well Known Text
    ATTR = _geometry
    OGCVERSION = 1.1
    -> AttributeTrimmer
AttributeTrimmer
    TRIM_CHARS = fme_basicstring:16%3:MULTIPOLYGON ((()))
    TRIM_TO_NONE = Yes
    TRIM_TYPE = Both
    SRC_ATTRS = _geometry
    -> StringReplacer
StringReplacer
    FIND_TEXT = ,
    SRC_ATTRS = _geometry
    REPLACE_TEXT = " "
    REGEXP = no
    CASE = no
    -> AttributeCreator
Note: creer tijdelijke Dummy attributen voor datum en verplichte tekst velden
AttributeCreator
    ATTR_LIST = __dumydatum,2000-01-01T00:00:00,Other,other,srsDimension,2,AggregationType,table,srsName,EPSG:4258,lowerCorner,4.0 50.0,upperCorner,6.0 53.0,legalFoudationDate,fme_basicstring:13:@Value(datum),BaseName,NL.PS.WETLAND,DV,NatinalPark,designationScheme,NatinalPark,percentage,100,naam,fme_basicstring:12:@Value(naam),applicationSchema,simple,ProtectedClassification,natureConservation,ProtectedClassification2,ecological,ProtectedClassification3,landscape
    -> CoordinateSystemExtractor
CoordinateSystemExtractor
    CRDSYS_ATTR = _coordsys
    -> StringConcatenator_3
StringConcatenator_3
    PARM_LINE = fme_basicstring:3%11:id-@Value(gid)
    VAL_ATTR = attributeID
    -> UUIDGenerator
UUIDGenerator
    UUID_ATTR = _uuid
    -> StringConcatenator_2
StringConcatenator_2
    PARM_LINE = fme_basicstring:3%13:id-@Value(_uuid)
    VAL_ATTR = gmlID
    -> AttributeCreator_4
AttributeCreator_4
    ATTR_LIST = inspireID,fme_basicstring:10:@Value(nr)
    -> XMLTemplater
XMLTemplater
    OUTPUT_XML_HEADER = Yes
    VISIBLE_QUERY_VALIDATE = Yes
    ROOT_QUERY_EXPR:
      <ps:ProtectedSite xmlns:base="urn:x-inspire:specification:gmlas:BaseTypes:3.2"
      xmlns:gmd="http://www.isotc211.org/2005/gmd"
      xmlns:gml="http://www.opengis.net/gml/3.2"
      xmlns:gn="urn:x-inspire:specification:gmlas:GeographicalNames:3.0"
      xmlns:ps="urn:x-inspire:specification:gmlas:ProtectedSites:3.0"
      xmlns:gco="http://www.isotc211.org/2005/gco"
      xmlns:xlink="http://www.w3.org/1999/xlink"
      xmlns:xsi="http://www.w3.org/2001/XMLSchema-instance"
      xmlns:gss="http://www.isotc211.org/2005/gss"
      xmlns:gsr="http://www.isotc211.org/2005/gsr"
      xmlns:gts="http://www.isotc211.org/2005/gts"
      gml:id="id-951b1a51-03bc-4a7b-b37f-44e6968f89b9"
      xsi:schemaLocation="urn:x-inspire:specification:gmlas:BaseTypes:3.2 http://inspire.ec.europa.eu/schemas/base/3.2/BaseTypes.xsd
      urn:x-inspire:specification:gmlas:ProtectedSites:3.0 http://inspire.ec.europa.eu/schemas/ps/3.0/ProtectedSites.xsd
      urn:x-inspire:specification:gmlas:GeographicalNames:3.0 http://inspire.ec.europa.eu/schemas/gn/3.0/GeographicalNames.xsd" >
      <gml:identifier codeSpace="http://inspire.jrc.ec.europa.eu/">urn:x-inspire:object:id:{fme:get-attribute("BaseName")}
      </gml:identifier>
        <gml:name codeSpace=""><!-- String value. --></gml:name>
        <gml:boundedBy nilReason="">
          <gml:Envelope srsName="{fme:get-attribute("srsName")}" srsDimension="{fme:get-attribute("srsDimension")}" axisLabels="" uomLabels="">
            <gml:lowerCorner srsName="{fme:get-attribute("srsName")}" srsDimension="{fme:get-attribute("srsDimension")}" axisLabels="" uomLabels="">{fme:get-attribute("lowerCorner")}</gml:lowerCorner>
            <gml:upperCorner srsName="{fme:get-attribute("srsName")}" srsDimension="{fme:get-attribute("srsDimension")}" axisLabels="" uomLabels="">{fme:get-attribute("upperCorner")}</gml:upperCorner>
            <!-- End Choice 2 -->
          </gml:Envelope>
          <!-- End Choice 1 -->
        </gml:boundedBy>
        <gml:location nilReason="" gml:remoteSchema="" xlink:type="simple" xlink:href="" xlink:title="" xlink:show="{fme:get-attribute("Other")}" xlink:actuate="{fme:get-attribute("Other")}">
              <gml:MultiSurface aggregationType="{fme:get-attribute("AggregationType")}" srsName="{fme:get-attribute("srsName")}" srsDimension="{fme:get-attribute("srsDimension")}" axisLabels="" uomLabels="" gml:id="{fme:get-attribute("gmlID")}2">
            <!-- AggregationType moet nog gecontroleerd worden -->
            <gml:metaDataProperty about="" nilReason="" gml:remoteSchema="" xlink:type="simple" xlink:href="" xlink:title="" xlink:show="{fme:get-attribute("Other")}" xlink:actuate="{fme:get-attribute("Other")}">
              <gml:GenericMetaData gml:id="{fme:get-attribute("gmlID")}3">
              </gml:GenericMetaData>
            </gml:metaDataProperty>
            <gml:description nilReason="" gml:remoteSchema="" xlink:type="simple" xlink:href="" xlink:title="" xlink:show="{fme:get-attribute("Other")}" xlink:actuate="{fme:get-attribute("Other")}"><!-- String value. --></gml:description>
            <gml:descriptionReference owns="false" nilReason="" gml:remoteSchema="" xlink:type="simple" xlink:href="" xlink:title="" xlink:show="{fme:get-attribute("Other")}" xlink:actuate="{fme:get-attribute("Other")}"/>
            <gml:identifier codeSpace="">{fme:get-attribute("inspireID")}</gml:identifier>
            <gml:name codeSpace=""><!-- String value. --></gml:name>
            <gml:surfaceMember nilReason="" gml:remoteSchema="" xlink:type="simple" xlink:href="" xlink:title="" xlink:show="{fme:get-attribute("Other")}" xlink:actuate="{fme:get-attribute("Other")}" owns="false">
            </gml:surfaceMember>
          </gml:MultiSurface>
        </gml:location>
        <ps:geometry nilReason="" gml:remoteSchema="" xlink:type="simple" xlink:href="" xlink:title="" xlink:show="{fme:get-attribute("Other")}" xlink:actuate="{fme:get-attribute("Other")}" owns="false">
          <gml:MultiSurface aggregationType="{fme:get-attribute("AggregationType")}" srsName="{fme:get-attribute("srsName")}" srsDimension="{fme:get-attribute("srsDimension")}" axisLabels="" uomLabels="" gml:id="{fme:get-attribute("gmlID")}4">
            <!-- AggregationType moet nog gecontroleerd worden -->
            <gml:metaDataProperty about="" nilReason="" gml:remoteSchema="" xlink:type="simple" xlink:href="" xlink:title="" xlink:show="{fme:get-attribute("Other")}" xlink:actuate="{fme:get-attribute("Other")}">
              <gml:GenericMetaData gml:id="{fme:get-attribute("gmlID")}5">
              </gml:GenericMetaData>
            </gml:metaDataProperty>
                  <gml:surfaceMember>
            <gml:Surface gml:id="{fme:get-attribute("gmlID")}6">
            <gml:patches>
      <gml:PolygonPatch>
      <gml:exterior>
      <gml:LinearRing>
      <gml:posList>{fme:get-attribute("_geometry")}</gml:posList>
      </gml:LinearRing>
      </gml:exterior>
      </gml:PolygonPatch>
      </gml:patches>
      </gml:Surface>
      </gml:surfaceMember>
      </gml:MultiSurface>
        </ps:geometry>
        <ps:inspireID>
          <base:Identifier>
            <base:localId><!-- String value. --></base:localId>
            <base:namespace><!-- String value. --></base:namespace>
            <base:versionId nilReason=""><!-- String value. --></base:versionId>
          </base:Identifier>
        </ps:inspireID>
        <ps:legalFoundationDate nilReason="">{fme:get-attribute("legalFoudationDate")}</ps:legalFoundationDate>
        <!-- dit is een dummy datum. Deze moet nog worden aangepast -->
        <ps:legalFoundationDocument nilReason="" owns="false">
          <gmd:CI_Citation id="{fme:get-attribute("gmlID")}7" uuid="">
            <gmd:title gco:nilReason="">
              <gco:CharacterString><!-- String value. --></gco:CharacterString>
            </gmd:title>
            <gmd:alternateTitle gco:nilReason="">
              <gco:CharacterString><!-- String value. --></gco:CharacterString>
            </gmd:alternateTitle>
            <gmd:date uuidref="" xlink:type="simple" xlink:href="" xlink:title="" xlink:show="{fme:get-attribute("Other")}" xlink:actuate="{fme:get-attribute("Other")}">
              <gmd:CI_Date id="{fme:get-attribute("attributeID")}1" uuid="">
                <gmd:date gco:nilReason="">
                </gmd:date>
                <gmd:dateType>
                  <gmd:CI_DateTypeCode codeList="" codeListValue="" codeSpace=""><!-- String value. --></gmd:CI_DateTypeCode>
                </gmd:dateType>
              </gmd:CI_Date>
            </gmd:date>
            <gmd:edition gco:nilReason="">
              <gco:CharacterString><!-- String value. --></gco:CharacterString>
            </gmd:edition>
            <gmd:editionDate gco:nilReason="">
            </gmd:editionDate>
            <gmd:identifier uuidref="" xlink:type="simple" xlink:href="" xlink:title="" xlink:show="{fme:get-attribute("Other")}" xlink:actuate="{fme:get-attribute("Other")}">
              <gmd:MD_Identifier id="{fme:get-attribute("attributeID")}2" uuid="">
                <gmd:authority uuidref="" xlink:type="simple" xlink:href="" xlink:title="" xlink:show="{fme:get-attribute("Other")}" xlink:actuate="{fme:get-attribute("Other")}">
                </gmd:authority>
                <gmd:code gco:nilReason="">
                  <gco:CharacterString><!-- String value. --></gco:CharacterString>
                </gmd:code>
              </gmd:MD_Identifier>
            </gmd:identifier>
            <gmd:citedResponsibleParty uuidref="" xlink:type="simple" xlink:href="" xlink:title="" xlink:show="{fme:get-attribute("Other")}" xlink:actuate="{fme:get-attribute("Other")}">
              <gmd:CI_ResponsibleParty id="{fme:get-attribute("attributeID")}3" uuid="">
                <gmd:individualName gco:nilReason="">
                  <gco:CharacterString><!-- String value. --></gco:CharacterString>
                </gmd:individualName>
                <gmd:organisationName gco:nilReason="">
                  <gco:CharacterString><!-- String value. --></gco:CharacterString>
                </gmd:organisationName>
                <gmd:positionName gco:nilReason="">
                  <gco:CharacterString><!-- String value. --></gco:CharacterString>
                </gmd:positionName>
                <gmd:contactInfo uuidref="" xlink:type="simple" xlink:href="" xlink:title="" xlink:show="{fme:get-attribute("Other")}" xlink:actuate="{fme:get-attribute("Other")}">
                  <gmd:CI_Contact id="{fme:get-attribute("attributeID")}4" uuid="">
                    <gmd:phone uuidref="" xlink:type="simple" xlink:href="" xlink:title="" xlink:show="{fme:get-attribute("Other")}" xlink:actuate="{fme:get-attribute("Other")}">
                      <gmd:CI_Telephone id="{fme:get-attribute("attributeID")}5" uuid="">
                        <gmd:voice gco:nilReason="">
                          <gco:CharacterString><!-- String value. --></gco:CharacterString>
                        </gmd:voice>
                        <gmd:facsimile gco:nilReason="">
                          <gco:CharacterString><!-- String value. --></gco:CharacterString>
                        </gmd:facsimile>
                      </gmd:CI_Telephone>
                    </gmd:phone>
                    <gmd:address uuidref="" xlink:type="simple" xlink:href="" xlink:title="" xlink:show="{fme:get-attribute("Other")}" xlink:actuate="{fme:get-attribute("Other")}">
                      <gmd:CI_Address id="{fme:get-attribute("attributeID")}6" uuid="">
                        <gmd:deliveryPoint gco:nilReason="">
                          <gco:CharacterString><!-- String value. --></gco:CharacterString>
                        </gmd:deliveryPoint>
                        <gmd:city gco:nilReason="">
                          <gco:CharacterString><!-- String value. --></gco:CharacterString>
                        </gmd:city>
                        <gmd:administrativeArea gco:nilReason="">
                          <gco:CharacterString><!-- String value. --></gco:CharacterString>
                        </gmd:administrativeArea>
                        <gmd:postalCode gco:nilReason="">
                          <gco:CharacterString><!-- String value. --></gco:CharacterString>
                        </gmd:postalCode>
                        <gmd:country gco:nilReason="">
                          <gco:CharacterString><!-- String value. --></gco:CharacterString>
                        </gmd:country>
                        <gmd:electronicMailAddress gco:nilReason="">
                          <gco:CharacterString><!-- String value. --></gco:CharacterString>
                        </gmd:electronicMailAddress>
                      </gmd:CI_Address>
                    </gmd:address>
                    <gmd:onlineResource uuidref="" xlink:type="simple" xlink:href="" xlink:title="" xlink:show="{fme:get-attribute("Other")}" xlink:actuate="{fme:get-attribute("Other")}">
                      <gmd:CI_OnlineResource id="{fme:get-attribute("attributeID")}7" uuid="">
                        <gmd:linkage>
                          <gmd:URL><!-- Any URI value. --></gmd:URL>
                        </gmd:linkage>
                        <gmd:protocol gco:nilReason="">
                          <gco:CharacterString><!-- String value. --></gco:CharacterString>
                        </gmd:protocol>
                        <gmd:applicationProfile gco:nilReason="">
                          <gco:CharacterString><!-- String value. --></gco:CharacterString>
                        </gmd:applicationProfile>
                        <gmd:name gco:nilReason="">
                          <gco:CharacterString><!-- String value. --></gco:CharacterString>
                        </gmd:name>
                        <gmd:description gco:nilReason="">
                          <gco:CharacterString><!-- String value. --></gco:CharacterString>
                        </gmd:description>
                        <gmd:function>
                          <gmd:CI_OnLineFunctionCode codeList="" codeListValue="" codeSpace=""><!-- String value. --></gmd:CI_OnLineFunctionCode>
                        </gmd:function>
                      </gmd:CI_OnlineResource>
                    </gmd:onlineResource>
                    <gmd:hoursOfService gco:nilReason="">
                      <gco:CharacterString><!-- String value. --></gco:CharacterString>
                    </gmd:hoursOfService>
                    <gmd:contactInstructions gco:nilReason="">
                      <gco:CharacterString><!-- String value. --></gco:CharacterString>
                    </gmd:contactInstructions>
                  </gmd:CI_Contact>
                </gmd:contactInfo>
                <gmd:role>
                  <gmd:CI_RoleCode codeList="" codeListValue="" codeSpace=""><!-- String value. --></gmd:CI_RoleCode>
                </gmd:role>
              </gmd:CI_ResponsibleParty>
            </gmd:citedResponsibleParty>
            <gmd:presentationForm>
              <gmd:CI_PresentationFormCode codeList="" codeListValue="" codeSpace=""><!-- String value. --></gmd:CI_PresentationFormCode>
            </gmd:presentationForm>
            <gmd:series uuidref="" xlink:type="simple" xlink:href="" xlink:title="" xlink:show="{fme:get-attribute("Other")}" xlink:actuate="{fme:get-attribute("Other")}">
              <gmd:CI_Series id="{fme:get-attribute("attributeID")}8" uuid="">
                <gmd:name gco:nilReason="">
                  <gco:CharacterString><!-- String value. --></gco:CharacterString>
                </gmd:name>
                <gmd:issueIdentification gco:nilReason="">
                  <gco:CharacterString><!-- String value. --></gco:CharacterString>
                </gmd:issueIdentification>
                <gmd:page gco:nilReason="">
                  <gco:CharacterString><!-- String value. --></gco:CharacterString>
                </gmd:page>
              </gmd:CI_Series>
            </gmd:series>
            <gmd:otherCitationDetails gco:nilReason="">
              <gco:CharacterString><!-- String value. --></gco:CharacterString>
            </gmd:otherCitationDetails>
            <gmd:collectiveTitle gco:nilReason="">
              <gco:CharacterString><!-- String value. --></gco:CharacterString>
            </gmd:collectiveTitle>
            <gmd:ISBN gco:nilReason="">
              <gco:CharacterString><!-- String value. --></gco:CharacterString>
            </gmd:ISBN>
            <gmd:ISSN gco:nilReason="">
              <gco:CharacterString><!-- String value. --></gco:CharacterString>
            </gmd:ISSN>
          </gmd:CI_Citation>
        </ps:legalFoundationDocument>
        <ps:siteDesignation nilReason="">
          <ps:DesignationType>
            <ps:designationScheme codeSpace="">{fme:get-attribute("designationScheme")}</ps:designationScheme>
            <ps:designation codeSpace="">{fme:get-attribute("DV")}</ps:designation>
            <ps:percentageUnderDesignation>{fme:get-attribute("percentage")}</ps:percentageUnderDesignation>
          </ps:DesignationType>
        </ps:siteDesignation>
        <ps:siteName nilReason="">
          <gn:GeographicalName>
            <gn:language nilReason=""><!-- String value. --></gn:language>
            <gn:nativeness nilReason="" codeSpace=""><!-- String value. --></gn:nativeness>
            <gn:nameStatus nilReason="" codeSpace=""><!-- String value. --></gn:nameStatus>
            <gn:sourceOfName nilReason=""><!-- String value. --></gn:sourceOfName>
            <gn:pronunciation nilReason="">
              <gn:PronunciationOfName>
                <gn:pronunciationSoundLink nilReason=""><!-- Any URI value. --></gn:pronunciationSoundLink>
                <gn:pronunciationIPA nilReason=""><!-- String value. --></gn:pronunciationIPA>
              </gn:PronunciationOfName>
            </gn:pronunciation>
            <gn:spelling>
              <gn:SpellingOfName>
                <gn:text>{fme:get-attribute("naam")}</gn:text>
                <gn:script nilReason=""><!-- String value. --></gn:script>
                <gn:transliterationScheme nilReason=""><!-- String value. --></gn:transliterationScheme>
              </gn:SpellingOfName>
            </gn:spelling>
            <gn:grammaticalGender nilReason="" codeSpace=""><!-- String value. --></gn:grammaticalGender>
            <gn:grammaticalNumber nilReason="" codeSpace=""><!-- String value. --></gn:grammaticalNumber>
          </gn:GeographicalName>
        </ps:siteName>
        <ps:siteProtectionClassification nilReason="">{fme:get-attribute("ProtectedClassification")}</ps:siteProtectionClassification>
        <ps:siteProtectionClassification nilReason="">{fme:get-attribute("ProtectedClassification2")}</ps:siteProtectionClassification>
        <ps:siteProtectionClassification nilReason="">{fme:get-attribute("ProtectedClassification3")}</ps:siteProtectionClassification>
      </ps:ProtectedSite>
    RESULT_ATTRIBUTE = _result
    -> AttributeCreator_2
AttributeCreator_2
    ATTR_LIST = ft_type,9
    -> BinaryEncoder
BinaryEncoder
    DEST_ATTR = binary_object
    ENCODING_TYPE = HEX
    ATTR_TO_ENCODE = _result
    -> inspire_ps.gml_objects (writer POSTGIS_2)
inspire_ps.gml_objects (writer POSTGIS_2)
    attributes: id serial,PRIKEY, gml_id text,PRIKEY, ft_type int2, gml_bounded_by char(80),GIST, binary_object bytea
