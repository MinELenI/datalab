FME workspace postgres2XML_compleet.fmw

Parameters:
- LOG_FILE = D:\Projects\PDOK\AdminUnits\Scripts\Log\AU_compleet.log   # Log File
- DestDataset_TEXTLINE = D:\Projects\PDOK\AdminUnits\Scripts\XML_uit\AU_compleet.xml   # Destination Text File
- FT_TYPE =   # Feature type

Readers:
- POSTGRES_1: POSTGRES from pdok

Writers:
- TEXTLINE_1: TEXTLINE to $(DestDataset_TEXTLINE)

Creator
    NUM = 1
    GEOMTYPE = Geometry Object
    CREATED -> AttributeCreator
AttributeCreator
    ATTR_LIST:
      text_line_data,<?xml version="1.0" encoding="UTF-8"?>
      <base:SpatialDataSet xmlns:base="urn:x-inspire:specification:gmlas:BaseTypes:3.2"
      xmlns:gmd="http://www.isotc211.org/2005/gmd"
      xmlns:gml="http://www.opengis.net/gml/3.2"
      xmlns:gn="urn:x-inspire:specification:gmlas:GeographicalNames:3.0"
      xmlns:ps="urn:x-inspire:specification:gmlas:ProtectedSites:3.0"
      xmlns:gco="http://www.isotc211.org/2005/gco"
      xmlns:xlink="http://www.w3.org/1999/xlink"
      xmlns:xsi="http://www.w3.org/2001/XMLSchema-instance"
      xmlns:gss="http://www.isotc211.org/2005/gss"
      xmlns:gsr="http://www.isotc211.org/2005/gsr"
      xmlns:gts="http://www.isotc211.org/2005/gts"
      xsi:schemaLocation="urn:x-inspire:specification:gmlas:BaseTypes:3.2 http://inspire.ec.europa.eu/schemas/base/3.2/BaseTypes.xsd
      urn:x-inspire:specification:gmlas:ProtectedSites:3.0 http://inspire.ec.europa.eu/schemas/ps/3.0/ProtectedSites.xsd
      urn:x-inspire:specification:gmlas:GeographicalNames:3.0 http://inspire.ec.europa.eu/schemas/gn/3.0/GeographicalNames.xsd"
       gml:id="NL.DLG.PS">
        <base:identifier>
          <base:Identifier>
            <base:localId>0</base:localId>
            <base:namespace>NL.DLG.PS</base:namespace>
          </base:Identifier>
        </base:identifier>
        <base:metadata xsi:nil="true"/>
    -> text_line (writer TEXTLINE_1)
inspire_ps.gml_objects (reader POSTGRES_1)
    attributes: id serial,PRIKEY, gml_id text,PRIKEY, ft_type int2, binary_object bytea, gml_bounded_by char(80),GIST
    -> BinaryDecoder
BinaryDecoder
    ATTR_ENCODING = utf-8
    ATTR_TO_DECODE = binary_object
    ENCODING_TYPE = HEX
    DEST_ATTR = _decoded
    -> StringConcatenator
StringConcatenator
    PARM_LINE:
        <base:member>
      @Value(_decoded)
      </base:member>
    VAL_ATTR = text_line_data
    -> text_line (writer TEXTLINE_1)
Creator_2
    NUM = 1
    GEOMTYPE = Geometry Object
    CREATED -> AttributeCreator_2
AttributeCreator_2
    ATTR_LIST = text_line_data,</base:SpatialDataSet>
    -> text_line (writer TEXTLINE_1)
text_line (writer TEXTLINE_1)
    attributes: text_line_data buffer
