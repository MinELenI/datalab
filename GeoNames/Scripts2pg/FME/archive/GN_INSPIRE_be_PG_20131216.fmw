FME workspace GN_INSPIRE_be_PG_20131216.fmw

Parameters:
- LOG_FILE =   # Log File
- MAX_FEATURES =   # Max Features to Read

Readers:
- POSTGIS_2: POSTGIS from pdok

Writers:
- POSTGIS_1: POSTGIS to pdok

top10nl.top10nl_wegdeel_vlakken (reader POSTGIS_2)
    attributes: ogc_fid serial,PRIKEY, identifica char(25), id_nr float8, aantalrijs float8, fysiekvoor float8, fysiekvo_1 char(60), gescheiden char(3), hoofdverke float8, hoofdver_1 char(120), typeinfras float8, typeinfr_1 char(25), typeweg_c1 float8, typeweg char(120), verharding float8, verhbreedt float8, verhardi_1 char(15), verhardi_2 float8, verhardi_3 char(25), afritnumme char(12), awegnummer char(40), nwegnummer char(20), ewegnummer char(20), swegnummer char(10), straatnaam char(254), afritnaam char(100), brugnaam char(100), knooppuntn char(100), tunnelnaam char(100), dimensie char(2), hoogtenive float8,
      status_cod float8, status char(35), objectbegi date, objecteind date, versiebegi date, versieeind date, bronactual date, bronbeschr char(250), bronnauwke float8, brontype_c float8, brontype char(15), symbol float8, symbol_h0 float8, tdn_code float8, shape_leng float8, shape_area float8
    -> AttributeTrimmer_3
    -> AttributeTrimmer_5
    -> AttributeTrimmer_6
    -> AttributeTrimmer_7
AttributeTrimmer_5
    SRC_ATTRS = afritnaam
    TRIM_TO_NONE = Yes
    TRIM_TYPE = Both
    -> Tester_afritnaam
Tester_afritnaam
    TEST_MODE = Automatic
    TEST_DESCRIPTION = ""
    BOOL_OP = AND
    TEST_CLAUSE:
      TEST afritnaam ATTRIBUTE_EXISTS <Unused>
      TEST afritnaam NOT_ATTRIBUTE_IS_EMPTY <Unused>
      TEST afritnaam NOT_ATTRIBUTE_IS_NULL <Unused>
    PASSED -> AttributeCopier_7
AttributeCopier_7
    ATTR_LIST = naam,afritnaam
    -> AttributeCreator_2
AttributeTrimmer_6
    SRC_ATTRS = knooppuntn
    TRIM_TO_NONE = Yes
    TRIM_TYPE = Both
    -> Tester_knooppuntn
Tester_knooppuntn
    TEST_MODE = Automatic
    TEST_DESCRIPTION = ""
    BOOL_OP = AND
    TEST_CLAUSE:
      TEST knooppuntn ATTRIBUTE_EXISTS <Unused>
      TEST knooppuntn NOT_ATTRIBUTE_IS_EMPTY <Unused>
      TEST knooppuntn NOT_ATTRIBUTE_IS_NULL <Unused>
    PASSED -> AttributeCopier_9
AttributeCopier_9
    ATTR_LIST = naam,knooppuntn
    -> AttributeCreator_2
AttributeTrimmer_7
    SRC_ATTRS = straatnaam
    TRIM_TO_NONE = Yes
    TRIM_TYPE = Both
    -> Tester_straatnaam
Tester_straatnaam
    TEST_MODE = Automatic
    TEST_DESCRIPTION = ""
    BOOL_OP = AND
    TEST_CLAUSE:
      TEST straatnaam ATTRIBUTE_EXISTS <Unused>
      TEST straatnaam NOT_ATTRIBUTE_IS_EMPTY <Unused>
      TEST straatnaam NOT_ATTRIBUTE_IS_NULL <Unused>
    PASSED -> AttributeCopier_10
AttributeCopier_10
    ATTR_LIST = naam,straatnaam
    -> AttributeCreator_2
top10nl.top10nl_terreinen (reader POSTGIS_2)
    attributes: ogc_fid serial,PRIKEY, identifica char(25), id_nr float8, dimensie char(2), fysiekvoor float8, fysiekvo_1 char(15), hoogtenive float8, naam char(75), status_cod float8, status char(35), typelandge float8, typeland_1 char(60), voorkomen_ float8, voorkomen char(25), bronactual date, bronbeschr char(250), bronnauwke float8, brontype_c float8, brontype char(15), objectbegi date, objecteind date, versiebegi date, versieeind date, symbol float8, symbol_h0 float8,BTREE, tdn_code float8, shape_leng float8, shape_area float8
    -> AttributeTrimmer
top10nl.top10nl_gebouwen (reader POSTGIS_2)
    attributes: ogc_fid serial,PRIKEY, identifica char(25), id_nr float8, dimensie char(2), hoogte float8, hoogteklas float8, hoogtekl_1 char(10), hoogtenive float8, naam char(75), status_cod float8, status char(35), typegebouw float8,BTREE, typegebo_1 char(90), bronactual date, bronbeschr char(250), bronnauwke float8, brontype_c float8, brontype char(15), objectbegi date, objecteind date, versiebegi date, versieeind date, symbol float8, symbol_h0 float8, tdn_code float8, shape_leng float8, shape_area float8
    -> AttributeTrimmer
top10nl.top10nl_inrichtingselement_lijnen (reader POSTGIS_2)
    attributes: ogc_fid serial,PRIKEY, identifica char(25), id_nr float8, dimensie char(2), hoogte float8, hoogtenive float8, naam char(50), nummer char(30), status_cod float8, status char(35), typeinrele float8, typeinrich char(35), bronactual date, bronbeschr char(250), bronnauwke float8, brontype_c float8, brontype char(15), objectbegi date, objecteind date, versiebegi date, versieeind date, symbol float8, symbol_h0 float8, tdn_code float8, shape_leng float8
    -> AttributeTrimmer
top10nl.top10nl_inrichtingselement_punten (reader POSTGIS_2)
    attributes: ogc_fid serial,PRIKEY, identifica char(25), id_nr float8, dimensie char(2), hoogte float8, hoogtenive float8, naam char(50), nummer char(30), status_cod float8, status char(35), typeinrele float8, typeinrich char(35), bronactual date, bronbeschr char(250), bronnauwke float8, brontype_c float8, brontype char(15), objectbegi date, objecteind date, versiebegi date, versieeind date, symbol float8, symbol_h0 float8, tdn_code float8
    -> AttributeTrimmer
top10nl.top10nl_functioneelgebied_labels (reader POSTGIS_2)
    attributes: ogc_fid serial,PRIKEY, identifica char(25), id_nr float8, dimensie char(2), naam char(75), status_cod float8, status char(35), typefunctg float8,BTREE, typefuncti char(45), bronactual date, bronbeschr char(250), bronnauwke float8, brontype_c float8, brontype char(15), objectbegi date, objecteind date, versiebegi date, versieeind date, symbol float8, tdn_code float8
    -> AttributeTrimmer
top10nl.top10nl_waterdeel_vlakken (reader POSTGIS_2)
    attributes: gid serial,PRIKEY, identifica varchar(25), id_nr int4, breedte float8, breedtekla int4, breedtek_1 varchar(17), brugnaam varchar(100), dimensie varchar(2), functie_co int4, functie varchar(20), fysiekvoor int4, fysiekvo_1 varchar(35), hoofdafwat varchar(3), hoogtenive int2, naam varchar(75), scheepslaa int4, sluisnaam varchar(100), status_cod int4, status varchar(35), stroomrich int4, stroomri_1 varchar(40), typeinfras int4, typeinfr_1 varchar(22), typewater_ int4,BTREE, typewater varchar(30), voorkomenw int4, voorkome_1 varchar(12), bronactual date, bronbeschr varchar(250), bronnauwke int4,
      brontype_c int4, brontype varchar(15), objectbegi date, objecteind date, versiebegi date, versieeind date, symbol int4, symbol_h0 int4, tdn_code int4, shape_leng float8, shape_area float8
    -> AttributeTrimmer
top10nl.top10nl_waterdeel_lijnen (reader POSTGIS_2)
    attributes: gid serial,PRIKEY, __gid float8, id float8, identifica varchar(25), id_nr float8, breedte float8, breedtekla float8, breedtek_1 varchar(17), brugnaam varchar(100), dimensie varchar(2), functie_co float8, functie varchar(20), fysiekvoor float8, fysiekvo_1 varchar(35), hoofdafwat varchar(3), hoogtenive float8, naam varchar(75), scheepslaa float8, sluisnaam varchar(100), status_cod float8, status varchar(35), stroomrich float8, stroomri_1 varchar(40), typeinfras float8, typeinfr_1 varchar(22), typewater_ float8, typewater varchar(30), voorkomenw float8, voorkome_1 varchar(12), bronactual varchar(10),
      bronbeschr varchar(250), bronnauwke float8, brontype_c float8, brontype varchar(15), objectbegi date, objecteind varchar(10), versiebegi date, versieeind varchar(10), symbol float8, symbol_h0 float8, tdn_code float8, shape_leng float8
    -> AttributeTrimmer
AttributeTrimmer
    SRC_ATTRS = naam
    TRIM_TO_NONE = Yes
    TRIM_TYPE = Both
    -> Tester_naam
Tester_naam
    TEST_MODE = Automatic
    TEST_DESCRIPTION = ""
    BOOL_OP = AND
    TEST_CLAUSE:
      TEST naam ATTRIBUTE_EXISTS <Unused>
      TEST naam NOT_ATTRIBUTE_IS_EMPTY <Unused>
      TEST naam NOT_ATTRIBUTE_IS_NULL <Unused>
    PASSED -> AttributeCreator_2
top10nl.top10nl_spoorbaandeel_lijnen (reader POSTGIS_2)
    attributes: ogc_fid serial,PRIKEY, identifica char(25), id_nr float8, aantalspor float8, baanvaknaa char(25), brugnaam char(35), dimensie char(2), elektrific float8, electrific char(28), fysiekvoor float8, fysiekvo_1 char(60), hoogtenive float8, spoorbreed float8, spoorbre_1 char(18), status_cod float8, status char(35), tunnelnaam char(40), typeinfras float8, typeinfr_1 char(15), typespoorb float8,BTREE, typespoo_1 char(10), vervoerfun float8, vervoerf_1 char(25), bronactual date, bronbeschr char(250), bronnauwke float8, brontype_c float8, brontype char(15), objectbegi date, objecteind date,
      versiebegi date, versieeind date, symbol float8, symbol_h0 float8, tdn_code float8, shape_leng float8
    -> AttributeTrimmer_2
    -> AttributeTrimmer_3
    -> AttributeTrimmer_4
AttributeTrimmer_2
    SRC_ATTRS = baanvaknaa
    TRIM_TO_NONE = Yes
    TRIM_TYPE = Both
    -> Tester_baanvaknaa
Tester_baanvaknaa
    TEST_MODE = Automatic
    TEST_DESCRIPTION = ""
    BOOL_OP = AND
    TEST_CLAUSE:
      TEST baanvaknaa ATTRIBUTE_EXISTS <Unused>
      TEST baanvaknaa NOT_ATTRIBUTE_IS_EMPTY <Unused>
      TEST baanvaknaa NOT_ATTRIBUTE_IS_NULL <Unused>
    PASSED -> AttributeCopier_2
AttributeCopier_2
    ATTR_LIST = naam,baanvaknaa
    -> AttributeCreator_2
AttributeTrimmer_3
    SRC_ATTRS = brugnaam
    TRIM_TO_NONE = Yes
    TRIM_TYPE = Both
    -> Tester_brugnaam
Tester_brugnaam
    TEST_MODE = Automatic
    TEST_DESCRIPTION = ""
    BOOL_OP = AND
    TEST_CLAUSE:
      TEST brugnaam ATTRIBUTE_EXISTS <Unused>
      TEST brugnaam NOT_ATTRIBUTE_IS_EMPTY <Unused>
      TEST brugnaam NOT_ATTRIBUTE_IS_NULL <Unused>
    PASSED -> AttributeCopier_5
AttributeCopier_5
    ATTR_LIST = naam,brugnaam
    -> AttributeCreator_2
AttributeTrimmer_4
    SRC_ATTRS = tunnelnaam
    TRIM_TO_NONE = Yes
    TRIM_TYPE = Both
    -> Tester_tunnelnaam
Tester_tunnelnaam
    TEST_MODE = Automatic
    TEST_DESCRIPTION = ""
    BOOL_OP = AND
    TEST_CLAUSE:
      TEST tunnelnaam ATTRIBUTE_EXISTS <Unused>
      TEST tunnelnaam NOT_ATTRIBUTE_IS_EMPTY <Unused>
      TEST tunnelnaam NOT_ATTRIBUTE_IS_NULL <Unused>
    PASSED -> AttributeCopier_6
AttributeCopier_6
    ATTR_LIST = naam,tunnelnaam
    -> AttributeCreator_2
AttributeCreator_2
    ATTR_LIST = taal,NL
    -> AttributeCopier_12
AttributeCopier_12
    ATTR_LIST = type,typefuncti,type,typegebo_1,type,typespoo_1,type,typewater,type,typeweg,type,typeinrich
    -> StringReplacer
StringReplacer
    SRC_ATTRS = identifica
    REGEXP = no
    CASE = no
    FIND_TEXT = NL.TOP10NL.
    -> AttributeKeeper
AttributeKeeper
    KEEP_ATTRS = identifica,naam,type,objectbegi,versiebegi,taal
    -> DateFormatter
DateFormatter
    DATE_ATTR = objectbegi,versiebegi
    FMT = %Y-%m-%dT%H:%M:%S
    -> CsmapReprojector
Note: Reprojectie naar EPSG:4258
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> AttributeValueMapper
AttributeValueMapper
    DIRECTION = Forward (Source To Destination)
    VAL_ATTR = type_decoded
    DEFAULT_VALUE = other
    LUT = GPS kernnetpunt,other,RD punt,other,bank, ondiepte, plaat,hydrography,bron, wel,hydrography,camping, kampeerterrein,landcover,dam, koedam,hydrography,dierentuin, safaripark,landcover,gedenkteken, monument,other,geul, vaargeul,hydrography,greppel, droge sloot,hydrography,heg, haag,landcover,heuvel, berg,landform,kaap, hoek,hydrography,kade, wal,landform,kas, warenhuis,building,kazerne, legerplaats,landcover,kerncentrale, kernreactor,building,kilometerpaal spoorweg,other,kilometerpaal water,other,kliniek, inrichting, sanatorium,building,klooster, abdij,building,kogelvanger schietbaan,other,licht, lichtopstand,other,lokale weg,transportNetwork,markant object,other,meer, plas, ven, vijver,hydrography,militair gebouw,building,militair oefengebied, schietterrein,landcover,natuurgebied, natuurreservaat,protectedSite,parkeerdak, parkeerdek, parkeergarage,building,plaats, bewoond oord,populatedPlace,psychiatrisch ziekenhuis, psychiatrisch centrum,building,radiotoren, televisietoren,building,regionale weg,transportNetwork,religieus gebouw,building,rolbaan, platform,transportNetwork,sportterrein, sportcomplex,landcover,startbaan, landingsbaan,transportNetwork,steile rand, aardrand,landform,streek, veld,landform,talud, hoogteverschil,landform,vliegveld, luchthaven,landcover,windmolen: korenmolen,building,windmolen: watermolen,building,zeegat, zeearm,hydrography,zichtbaar wrak,other,zwembad complex,building,aanlegsteiger,landcover,afrit,transportNetwork,arboretum,landcover,autosnelweg,transportNetwork,baak,other,baanvak,transportNetwork,bedrijventerrein,landcover,begraafplaats,landcover,bezoekerscentrum,building,bomenrij,landcover,boom,landcover,bosgebied,landcover,boswachterij,landcover,brandtoren,building,brug,transportNetwork,bungalowpark,populatedPlace,bunker,building,buurtschap,populatedPlace,caravanpark,populatedPlace,circuit,landcover,crematorium,building,crossbaan,landcover,deelraadsecretarie,building,dieptelijn,other,dieptepunt,other,dok,hydrography,droogvallend,hydrography,duingebied,landform,dukdalf,hydrography,eendenkooi,hydrography,eiland,landform,elektriciteitscentrale,building,emplacement,landcover,erebegraafplaats,landcover,fabriek,building,fort,building,gaswinning,landcover,gebouwencomplex,building,geluidswering,other,gemaal,building,gemeentehuis,building,gevangenis,building,golfmeetpaal,other,golfterrein,landcover,grafheuvel,landform,grenspunt,other,grindwinning,landcover,groeve,landcover,haven,hydrography,heemtuin,landcover,heidegebied,landcover,hekwerk,landcover,helikopterlandingsplatform,other,helikopterlandingsterrein,landcover,hoofdweg,transportNetwork,hoogspanningsleiding,other,hoogspanningsmast,other,hoogtelijn,other,hoogtepunt,other,hotel,building,huizenblok,populatedPlace,huizengroep,populatedPlace,hulpsecretarie,building,hunebed,landcover,ijsbaan,landcover,infiltratiegebied,hydrography,jachthaven,hydrography,kaap,hydrography,kabelbaan,transportNetwork,kabelbaanmast,other,kapel,building,kartingbaan,landcover,kasteel,building,kerk,building,kilometerpaal,other,kilometerraaibord,other,kilometerraaipaal,other,klokkentoren,building,knooppunt,transportNetwork,koeltoren,building,koepel,building,kraan,building,kruis,other,kunstijsbaan,building,laadperron,landcover,laagwaterlijn,other,landgoed,landcover,lichttoren,building,luchtwachttoren,building,manege,building,metro,transportNetwork,metrostation,building,mijn,landcover,mosselbank,hydrography,motel,building,museum,building,muur,building,oliepompinstallatie,other,oliewinning,landcover,onbekend,other,openluchtmuseum,landcover,openluchttheater,other,overig,other,paal,other,paalwerk,other,park,landcover,peil,other,peilmeetstation,building,peilschaal,other,pijler,building,pinetum,landcover,plantsoen,landcover,polder,landform,politiebureau,building,pompstation,building,postkantoor,building,productie-installatie,building,radarpost,building,radartoren,building,radiobaken,other,radiotelescoop,building,recreatiecentrum,building,recreatiegebied,landcover,reddingboothuisje,building,remise,building,renbaan,landcover,ruïne,building,schaapskooi,building,schietbaan,other,school,building,schoorsteen,building,seinmast,other,skibaan,other,slipschool,other,sluisdeur,hydrography,sluizencomplex,hydrography,sporthal,building,stadion,building,stadskantoor,building,station,building,stormvloedkering,building,stortplaats,landcover,straat,transportNetwork,strandpaal,other,stuw,hydrography,tank,building,tankstation,building,telecommunicatietoren,building,tennispark,landcover,terp,landform,tol,transportNetwork,toren,building,tram,transportNetwork,transformatorstation,building,trein,transportNetwork,treinstation,building,tuincentrum,building,tunnel,transportNetwork,uitzichttoren,building,universiteit,building,veiling,building,verkeersgeleider,other,verkeerstoren,building,verzorgingsplaats,other,viskwekerij,hydrography,vlampijp,building,vliedberg,landform,volkstuinen,landcover,vuurtoren,building,waterloop,hydrography,waterradmolen,building,watertoren,building,wegafsluiting,transportNetwork,wegenwachtstation,building,wegrestaurant,building,wegwijzer,transportNetwork,werf,building,wildwissel,other,windmolen,building,windmolentje,other,windturbine,building,windturbinepark,landcover,woonwagencentrum,populatedPlace,woonwijk,populatedPlace,zandwinning,landcover,zee,hydrography,zenderpark,landcover,zendmast,building,zendtoren,building,ziekenhuis,building,zoutwinning,landcover,zuiveringsinstallatie,building,zweefvliegveldterrein,landcover,zwembad,building
    SRC = type
    -> AttributeCreator
AttributeCreator
    ATTR_LIST = brontekst,De Basisregistratie Topografie (BRT) bestaat uit digitale topografische bestanden op verschillende schaalniveaus. Het uit de BRT afgeleide TOP10NL is een digitaal objectgericht topografisch bestand wat ten grondslag ligt aan de topografische kaartseries 1:10.000 en 1:25.000 en wat veelvuldig in diverse GIS- en CAD-systemen wordt gebruikt voor ondergrond, analyse-, en beheers- en planningsactiviteiten.
    -> GeometryExtractor
GeometryExtractor
    ATTR = _geometry
    OMIT_NAMESPACES_DISPLAY = Yes
    KIND_LONG = GML v3.2.1
    -> XMLTemplater_3
XMLTemplater_3
    RESULT_ATTRIBUTE = binary_object
    ROOT_QUERY_EXPR:
      <gn:NamedPlace xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2" gml:id="NL.KAD.BRT.GeographicalNames.{fme:get-attribute('identificatie')}">
        <gml:identifier codeSpace="http://inspire.jrc.ec.europa.eu/">
             urn:x-inspire:object:id:NL.KAD.BRT.GeographicalNames.{fme:get-attribute('identifica')}
        </gml:identifier>
        <gn:beginLifespanVersion nilReason="">{fme:get-attribute("objectbegi")}</gn:beginLifespanVersion>
        <gn:geometry>{fme:get-attribute("_geometry")}</gn:geometry>
        <gn:inspireId>
          <base:Identifier>
            <base:localId>{fme:get-attribute('identifica')}</base:localId>
            <base:namespace>NL.KAD.BRT.GeographicalNames</base:namespace>
            <base:versionId>{fme:get-attribute("versiebegi")}</base:versionId>
          </base:Identifier>
        </gn:inspireId>
        <gn:leastDetailedViewingResolution nilReason="other:unpopulated" owns="false">
          <gmd:MD_Resolution>
            <gmd:equivalentScale></gmd:equivalentScale>
          </gmd:MD_Resolution>
        </gn:leastDetailedViewingResolution>
        <gn:localType gco:nilReason="other:unpopulated" uuidref="" xlink:type="simple" xlink:href="" xlink:role="none" xlink:arcrole="none" xlink:title="none" xlink:show="none" xlink:actuate="none">
          <gmd:LocalisedCharacterString></gmd:LocalisedCharacterString>
        </gn:localType>
        <gn:mostDetailedViewingResolution nilReason="other:unpopulated" owns="false">
          <gmd:MD_Resolution>
            <gmd:equivalentScale></gmd:equivalentScale>
          </gmd:MD_Resolution>
        </gn:mostDetailedViewingResolution>
        <gn:name>
          <gn:GeographicalName>
            <gn:language>{fme:get-attribute("taal")}</gn:language>
            <gn:nativeness>endonym</gn:nativeness>
            <gn:nameStatus  nilReason="other:unpopulated"></gn:nameStatus>
            <gn:sourceOfName>{fme:get-attribute('brontekst')}</gn:sourceOfName>
            <gn:pronunciation xmlns:xsi="http://www.w3.org/2001/XMLSchema-instance" nilReason="other:unpopulated" xsi:nil="true"/>
            <gn:spelling>
              <gn:SpellingOfName>
                <gn:text>{fme:get-attribute('naam')}</gn:text>
                 <gn:script>Latn</gn:script>
              </gn:SpellingOfName>
            </gn:spelling>
          </gn:GeographicalName>
        </gn:name>
        <gn:type codeSpace="urn:x-inspire:specification:gmlas:GeographicalNames:3.0/NamedPlaceTypeValue">{fme:get-attribute("type_decoded")}</gn:type>
      </gn:NamedPlace>
    VISIBLE_QUERY_VALIDATE = No
    OUTPUT_XML_HEADER = No
    -> AttributeCreator_3
Note: ft=63 voor NamedPlace
AttributeCreator_3
    ATTR_LIST = ft_type,63,gml_id,NL.KAD.BRT.GeographicalNames.@Value(identifica)
    -> BoundingBoxReplacer
BoundingBoxReplacer
    BOXTYPE = Bounding Box
    BOX -> AttributeExpressionRemover
Note: Verwijderen alle originele / postgres attributen
AttributeExpressionRemover
    ATTR_EXP = postgis*
    -> BinaryEncoder
BinaryEncoder
    ENCODING_TYPE = HEX
    ATTR_TO_ENCODE = binary_object
    DEST_ATTR = binary_object
    -> inspire_gn.gml_objects (writer POSTGIS_1)
inspire_gn.gml_objects (writer POSTGIS_1)
    attributes: id serial,PRIKEY, gml_id text,none, ft_type int2, binary_object bytea
