FME workspace GN_INSPIRE_20130327.fmw

Parameters:
- SourceDataset_GML = D:\Projects\PDOK\GeoNames\Scripts2pg\DATA\*.gml   # Source Geography Markup Language (GML) File(s)
- MAX_FEATURES =   # Max Features to Read
- LOG_FILE =   # Log File

Readers:
- GML_1: GML from $(SourceDataset_GML)

Writers:
- POSTGIS_1: POSTGIS to pdok

GeografischGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalInwoners xml_int32, geometrieVlak xml_geometry, labelPunt xml_geometry, naamNL{} xml_buffer, typeGeografischGebied xml_char(23), naamFries{} xml_buffer
    -> StringReplacer
StringReplacer
    SRC_ATTRS = identificatie
    REGEXP = no
    CASE = no
    FIND_TEXT = NL.TOP10NL.
    -> AttributeCopier
AttributeCopier
    ATTR_LIST = NAAM,naamNL{0}
    -> AttributeKeeper
AttributeKeeper
    KEEP_ATTRS = identificatie,bronbeschrijving,objectBeginTijd,objectEindTijd,typeGeografischGebied,NAAM
    -> DateFormatter
DateFormatter
    DATE_ATTR = objectBeginTijd,objectEindTijd
    FMT = %Y-%m-%dT%H:%M:%S
    -> CsmapReprojector
Note: Reprojectie naar EPSG:4258
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> CoordinateExtractor
CoordinateExtractor
    Y_ATTR = Y
    X_ATTR = X
    Z_DEFAULT = -9999
    Z_ATTR = _z
    IND = 0
    -> XMLTemplater_8
XMLTemplater_8
    RESULT_ATTRIBUTE = binary_object
    ROOT_QUERY_EXPR:
      <gn:NamedPlace xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2" gml:id="NL.KAD.TOP10NL.GeographicalNames.{fme:get-attribute('identificatie')}">
        <gml:identifier codeSpace="http://inspire.jrc.ec.europa.eu/">
             urn:x-inspire:object:id:NL.KAD.TOP10NL.GeographicalNames.{fme:get-attribute('identificatie')}
        </gml:identifier>
        <gn:beginLifespanVersion nilReason="">{fme:get-attribute("objectBeginTijd")}</gn:beginLifespanVersion>
        <gn:geometry>
          <gml:Point srsName="urn:ogc:def:crs:EPSG::4258" srsDimension="2" gml:id="NL.KAD.TOP10NL.GeographicalNames.{fme:get-attribute('identificatie')}_P">
            <gml:pos>{fme:get-attribute('Y')} {fme:get-attribute('X')}</gml:pos>
          </gml:Point>
        </gn:geometry>
        <gn:inspireId>
          <base:Identifier>
            <base:localId>{fme:get-attribute('identificatie')}</base:localId>
            <base:namespace>NL.KAD.TOP10NL.GeographicalNames</base:namespace>
            <base:versionId>0</base:versionId>
          </base:Identifier>
        </gn:inspireId>
        <gn:leastDetailedViewingResolution nilReason="other:unpopulated" owns="false">
          <gmd:MD_Resolution>
            <gmd:equivalentScale></gmd:equivalentScale>
          </gmd:MD_Resolution>
        </gn:leastDetailedViewingResolution>
        <gn:localType gco:nilReason="other:unpopulated" uuidref="" xlink:type="simple" xlink:href="" xlink:role="none" xlink:arcrole="none" xlink:title="none" xlink:show="none" xlink:actuate="none">
          <gmd:LocalisedCharacterString></gmd:LocalisedCharacterString>
        </gn:localType>
        <gn:mostDetailedViewingResolution nilReason="other:unpopulated" owns="false">
          <gmd:MD_Resolution>
            <gmd:equivalentScale></gmd:equivalentScale>
          </gmd:MD_Resolution>
        </gn:mostDetailedViewingResolution>
        <gn:name>
          <gn:GeographicalName>
            <gn:language>NL</gn:language>
            <gn:nativeness>endonym</gn:nativeness>
            <gn:nameStatus  nilReason="other:unpopulated"></gn:nameStatus>
            <gn:sourceOfName nilReason="">{fme:get-attribute('bronbeschrijving')}</gn:sourceOfName>
            <gn:pronunciation xmlns:xsi="http://www.w3.org/2001/XMLSchema-instance" nilReason="other:unpopulated" xsi:nil="true"/>
            <gn:spelling>
              <gn:SpellingOfName>
                <gn:text>{fme:get-attribute('NAAM')}</gn:text>
                 <gn:script>Latn</gn:script>
              </gn:SpellingOfName>
            </gn:spelling>
          </gn:GeographicalName>
        </gn:name>
        <gn:type nilReason="" codeSpace="">{fme:get-attribute("typeGeografischGebied")}</gn:type>
      </gn:NamedPlace>
    VISIBLE_QUERY_VALIDATE = No
    OUTPUT_XML_HEADER = No
    -> AttributeCreator_3
Note: ft=63 voor NamedPlace
AttributeCreator_3
    ATTR_LIST = ft_type,63,gml_id,NL.KAD.TOP10NL.GeographicalNames.@Value(identificatie)
    -> BinaryEncoder
BinaryEncoder
    ENCODING_TYPE = HEX
    ATTR_TO_ENCODE = binary_object
    DEST_ATTR = binary_object
    -> AttributeExpressionRemover
Note: Verwijderen alle originele / postgres attributen
AttributeExpressionRemover
    ATTR_EXP = postgis*
    -> inspire_gn.gml_objects (writer POSTGIS_1)
inspire_gn.gml_objects (writer POSTGIS_1)
    attributes: id serial,PRIKEY, gml_id text,none, ft_type int2, binary_object bytea
