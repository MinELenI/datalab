FME workspace GN_INSPIRE_20131129.fmw

Parameters:
- SourceDataset_GML = D:\Projects\PDOK\GeoNames\Scripts2pg\DATA\*.gml   # Source Geography Markup Language (GML) File(s)
- MAX_FEATURES =   # Max Features to Read
- LOG_FILE =   # Log File

Readers:
- GML_1: GML from $(SourceDataset_GML)

Writers:
- POSTGIS_1: POSTGIS to pdok

Terrein (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, fysiekVoorkomen{} xml_char(10), geometrieVlak xml_geometry, hoogteniveau xml_int32, naamFries{} xml_buffer, naamNL{} xml_buffer, typeLandgebruik xml_char(28), voorkomen{} xml_char(15)
    -> ListExploder
    -> ListExploder_5
Gebouw (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieVlak xml_geometry, hoogte xml_real64, hoogteklasse xml_char(8), hoogteniveau xml_int32, naamNL{} xml_buffer, naamFries{} xml_buffer, status xml_char(34), typeGebouw{} xml_char(47)
    -> ListExploder
    -> ListExploder_5
Hoogteverschil (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), lageZijde xml_geometry, hogeZijde xml_geometry
    -> ListExploder
    -> ListExploder_5
KadeOfWal (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometrieLijn xml_geometry
    -> ListExploder
    -> ListExploder_5
IsoHoogte (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometrieLijn xml_geometry
    -> ListExploder
    -> ListExploder_5
Inrichtingselement (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieLijn xml_geometry, geometriePunt xml_geometry, hoogte xml_real64, hoogteniveau xml_int32, naamNL{} xml_buffer, nummer{} xml_buffer, status xml_char(34), typeInrichtingselement xml_char(26), naamFries{} xml_buffer
    -> ListExploder
    -> ListExploder_5
OverigRelief (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometriePunt xml_geometry, geometrieLijn xml_geometry
    -> ListExploder
    -> ListExploder_5
FunctioneelGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieVlak xml_geometry, labelPunt xml_geometry, naamFries{} xml_buffer, naamNL{} xml_buffer, typeFunctioneelGebied xml_char(35)
    -> ListExploder
    -> ListExploder_5
HoogteOfDieptePunt (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometriePunt xml_geometry
    -> ListExploder
    -> ListExploder_5
RegistratiefGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieVlak xml_geometry, labelPunt xml_geometry, naamFries{} xml_buffer, naamNL{} xml_buffer, nummer{} xml_int32, typeRegistratiefGebied xml_char(16)
    -> ListExploder
    -> ListExploder_5
GeografischGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalInwoners xml_int32, geometrieVlak xml_geometry, labelPunt xml_geometry, naamNL{} xml_buffer, typeGeografischGebied xml_char(23), naamFries{} xml_buffer
    -> ListExploder
    -> ListExploder_5
Waterdeel (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, breedte xml_real64, breedteklasse xml_char(13), brugnaam xml_buffer, functie xml_char(16), fysiekVoorkomen{} xml_char(26), geometrieLijn xml_geometry, geometriePunt xml_geometry, geometrieVlak xml_geometry, hoofdafwatering xml_char(3), hoogteniveau xml_int32, naamFries{} xml_buffer, naamNL{} xml_buffer, scheepslaadvermogen xml_real64, sluisnaam xml_buffer, status xml_char(34), stroomrichting xml_char(33), typeInfrastructuurWaterdeel xml_char(18), typeWater xml_char(23),
      voorkomenWater xml_char(8)
    -> ListExploder
    -> ListExploder_5
ListExploder
    INDEX_ATTR = _element_index
    MODE = List Elements and Original Attributes
    LIST_ATTR = naamNL{}
    LIST_FOUND -> Tester
    NOT_FOUND -> Tester
Tester
    TEST_MODE = Automatic
    TEST_DESCRIPTION = ""
    BOOL_OP = OR
    TEST_CLAUSE = TEST naamNL NOT_ATTRIBUTE_IS_EMPTY <Unused>
    PASSED -> AttributeCopier_2
AttributeCopier_2
    ATTR_LIST = naam,naamNL
    -> AttributeCopier_12
ListExploder_5
    INDEX_ATTR = _element_index
    MODE = List Elements and Original Attributes
    LIST_ATTR = naamFries{}
    LIST_FOUND -> Tester_5
    NOT_FOUND -> Tester_5
Tester_5
    TEST_MODE = Automatic
    TEST_DESCRIPTION = ""
    BOOL_OP = OR
    TEST_CLAUSE = TEST naamFries NOT_ATTRIBUTE_IS_EMPTY <Unused>
    PASSED -> AttributeCopier_3
AttributeCopier_3
    ATTR_LIST = naam,naamFries
    -> AttributeCopier_12
Spoorbaandeel (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalSporen xml_int32, baanvaknaam{} xml_buffer, brugnaam{} xml_buffer, elektrificatie xml_char(21), fysiekVoorkomen{} xml_char(27), geometrieLijn xml_geometry, geometriePunt xml_geometry, hoogteniveau xml_int32, spoorbreedte xml_char(12), status xml_char(34), tunnelnaam{} xml_buffer, typeInfrastructuurSpoorbaandeel xml_char(10), typeSpoorbaan xml_char(7), vervoerfunctie xml_char(15)
    -> ListExploder_2
    -> ListExploder_3
    -> ListExploder_4
ListExploder_2
    INDEX_ATTR = _element_index
    MODE = List Elements and Original Attributes
    LIST_ATTR = baanvaknaam{}
    LIST_FOUND -> Tester_2
    NOT_FOUND -> Tester_2
Tester_2
    TEST_MODE = Automatic
    TEST_DESCRIPTION = ""
    BOOL_OP = OR
    TEST_CLAUSE = TEST baanvaknaam NOT_ATTRIBUTE_IS_EMPTY <Unused>
    PASSED -> AttributeCopier_4
AttributeCopier_4
    ATTR_LIST = naam,baanvaknaam
    -> AttributeCopier_12
ListExploder_3
    INDEX_ATTR = _element_index
    MODE = List Elements and Original Attributes
    LIST_ATTR = brugnaam{}
    LIST_FOUND -> Tester_3
    NOT_FOUND -> Tester_3
Tester_3
    TEST_MODE = Automatic
    TEST_DESCRIPTION = ""
    BOOL_OP = OR
    TEST_CLAUSE = TEST brugnaam NOT_ATTRIBUTE_IS_EMPTY <Unused>
    PASSED -> AttributeCopier_5
AttributeCopier_5
    ATTR_LIST = naam,brugnaam
    -> AttributeCopier_12
ListExploder_4
    INDEX_ATTR = _element_index
    MODE = List Elements and Original Attributes
    LIST_ATTR = tunnelnaam{}
    LIST_FOUND -> Tester_4
    NOT_FOUND -> Tester_4
Tester_4
    TEST_MODE = Automatic
    TEST_DESCRIPTION = ""
    BOOL_OP = OR
    TEST_CLAUSE = TEST tunnelnaam NOT_ATTRIBUTE_IS_EMPTY <Unused>
    PASSED -> AttributeCopier_6
AttributeCopier_6
    ATTR_LIST = naam,tunnelnaam
    -> AttributeCopier_12
Wegdeel (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalRijstroken xml_int32, afritnaam{} xml_buffer, afritnummer xml_buffer, aWegnummer{} xml_buffer, brugnaam{} xml_buffer, eWegnummer{} xml_buffer, fysiekVoorkomen{} xml_char(27), geometrieLijn xml_geometry, geometriePunt xml_geometry, geometrieVlak xml_geometry, gescheidenRijbaan xml_char(3), hartLijn xml_geometry, hartPunt xml_geometry, hoofdverkeersgebruik{} xml_char(27), hoogteniveau xml_int32, knooppuntnaam{} xml_buffer, nWegnummer{} xml_buffer, status xml_char(34),
      straatnaamFries{} xml_buffer, straatnaamNL{} xml_buffer, sWegnummer{} xml_buffer, tunnelnaam{} xml_buffer, typeInfrastructuurWegdeel xml_char(21), typeWeg{} xml_char(23), verhardingsbreedte xml_real64, verhardingsbreedteklasse xml_char(11), verhardingstype xml_char(12)
    -> ListExploder_6
    -> ListExploder_7
    -> ListExploder_8
    -> ListExploder_9
    -> ListExploder_10
ListExploder_6
    INDEX_ATTR = _element_index
    MODE = List Elements and Original Attributes
    LIST_ATTR = afritnaam{}
    LIST_FOUND -> Tester_6
    NOT_FOUND -> Tester_6
Tester_6
    TEST_MODE = Automatic
    TEST_DESCRIPTION = ""
    BOOL_OP = OR
    TEST_CLAUSE = TEST afritnaam NOT_ATTRIBUTE_IS_EMPTY <Unused>
    PASSED -> AttributeCopier_7
AttributeCopier_7
    ATTR_LIST = naam,afritnaam
    -> AttributeCopier_12
ListExploder_7
    INDEX_ATTR = _element_index
    MODE = List Elements and Original Attributes
    LIST_ATTR = brugnaam{}
    LIST_FOUND -> Tester_7
    NOT_FOUND -> Tester_7
Tester_7
    TEST_MODE = Automatic
    TEST_DESCRIPTION = ""
    BOOL_OP = OR
    TEST_CLAUSE = TEST brugnaam NOT_ATTRIBUTE_IS_EMPTY <Unused>
    PASSED -> AttributeCopier_8
AttributeCopier_8
    ATTR_LIST = naam,brugnaam
    -> AttributeCopier_12
ListExploder_8
    INDEX_ATTR = _element_index
    MODE = List Elements and Original Attributes
    LIST_ATTR = knooppuntnaam{}
    LIST_FOUND -> Tester_8
    NOT_FOUND -> Tester_8
Tester_8
    TEST_MODE = Automatic
    TEST_DESCRIPTION = ""
    BOOL_OP = OR
    TEST_CLAUSE = TEST knooppuntnaam NOT_ATTRIBUTE_IS_EMPTY <Unused>
    PASSED -> AttributeCopier_9
AttributeCopier_9
    ATTR_LIST = naam,knooppuntnaam
    -> AttributeCopier_12
ListExploder_9
    INDEX_ATTR = _element_index
    MODE = List Elements and Original Attributes
    LIST_ATTR = straatnaamNL{}
    LIST_FOUND -> Tester_9
    NOT_FOUND -> Tester_9
Tester_9
    TEST_MODE = Automatic
    TEST_DESCRIPTION = ""
    BOOL_OP = OR
    TEST_CLAUSE = TEST straatnaamNL NOT_ATTRIBUTE_IS_EMPTY <Unused>
    PASSED -> AttributeCopier_10
AttributeCopier_10
    ATTR_LIST = naam,straatnaamNL
    -> AttributeCopier_12
ListExploder_10
    INDEX_ATTR = _element_index
    MODE = List Elements and Original Attributes
    LIST_ATTR = straatnaamFries{}
    LIST_FOUND -> Tester_10
    NOT_FOUND -> Tester_10
Tester_10
    TEST_MODE = Automatic
    TEST_DESCRIPTION = ""
    BOOL_OP = OR
    TEST_CLAUSE = TEST straatnaamFries NOT_ATTRIBUTE_IS_EMPTY <Unused>
    PASSED -> AttributeCopier_11
AttributeCopier_11
    ATTR_LIST = naam,straatnaamFries
    -> AttributeCopier_12
AttributeCopier_12
    ATTR_LIST = type,typeGeografischGebied,type,typeFunctioneelGebied,type,typeGebouw{0},type,typeSpoorbaan,type,typeWater,type,typeWeg{0},type,typeInrichtingselement,type,typeRelief
    -> StringReplacer
StringReplacer
    SRC_ATTRS = identificatie
    REGEXP = no
    CASE = no
    FIND_TEXT = NL.TOP10NL.
    -> AttributeKeeper
AttributeKeeper
    KEEP_ATTRS = identificatie,bronbeschrijving,objectBeginTijd,versieBeginTijd,objectEindTijd,naam,type
    -> DateFormatter
DateFormatter
    DATE_ATTR = objectBeginTijd,versieBeginTijd,objectEindTijd
    FMT = %Y-%m-%dT%H:%M:%S
    -> CsmapReprojector
Note: Reprojectie naar EPSG:4258
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> AttributeValueMapper
AttributeValueMapper
    DIRECTION = Forward (Source To Destination)
    VAL_ATTR = type_decoded
    DEFAULT_VALUE = other
    LUT = bank, ondiepte, plaat,hydrography,geul, vaargeul,hydrography,heuvel, berg,landform,kaap, hoek,landform,meer, plas, ven, vijver,hydrography,plaats, bewoond oord,populatedPlace,streek, veld,landform,zeegat, zeearm,hydrography,bosgebied,landcover,buurtschap,populatedPlace,duingebied,landcover,eiland,landform,heidegebied,landcover,huizengroep,populatedPlace,onbekend,other,overig,other,polder,landform,terp,landform,vliedberg,landform,woonwijk,populatedPlace,zee,hydrography
    SRC = type
    -> AttributeCreator
AttributeCreator
    ATTR_LIST = brontekst,De Basisregistratie Topografie (BRT) bestaat uit digitale topografische bestanden op verschillende schaalniveaus. Het uit de BRT afgeleide TOP10NL is een digitaal objectgericht topografisch bestand wat ten grondslag ligt aan de topografische kaartseries 1:10.000 en 1:25.000 en wat veelvuldig in diverse GIS- en CAD-systemen wordt gebruikt voor ondergrond, analyse-, en beheers- en planningsactiviteiten.
    -> CoordinateSwapper
Note: Omkeren volgorde lat en lon voor GML
CoordinateSwapper
    SWAP_TYPE = X <-> Y
    -> GeometryFilter
GeometryFilter
    BREAK_AGG = No
    POINT -> CoordinateExtractor
    AREA -> DonutHoleExtractor
    ELLIPSE -> DonutHoleExtractor
    LINE -> CoordinateConcatenator_2
    ARC -> CoordinateConcatenator_2
CoordinateExtractor
    Y_ATTR = Y
    X_ATTR = X
    Z_DEFAULT = -9999
    Z_ATTR = _z
    IND = 0
    -> XMLTemplater_8
XMLTemplater_8
    RESULT_ATTRIBUTE = binary_object
    ROOT_QUERY_EXPR:
      <gn:NamedPlace xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2" gml:id="NL.KAD.BRT.GeographicalNames.{fme:get-attribute('identificatie')}">
        <gml:identifier codeSpace="http://inspire.jrc.ec.europa.eu/">
             urn:x-inspire:object:id:NL.KAD.BRT.GeographicalNames.{fme:get-attribute('identificatie')}
        </gml:identifier>
        <gn:beginLifespanVersion nilReason="">{fme:get-attribute("objectBeginTijd")}</gn:beginLifespanVersion>
        <gn:geometry>
          <gml:Point srsName="urn:ogc:def:crs:EPSG::4258" srsDimension="2" gml:id="NL.KAD.BRT.GeographicalNames.{fme:get-attribute('identificatie')}_P">
            <gml:pos>{fme:get-attribute('Y')} {fme:get-attribute('X')}</gml:pos>
          </gml:Point>
        </gn:geometry>
        <gn:inspireId>
          <base:Identifier>
            <base:localId>{fme:get-attribute('identificatie')}</base:localId>
            <base:namespace>NL.KAD.BRT.GeographicalNames</base:namespace>
            <base:versionId>{fme:get-attribute("versieBeginTijd")}</base:versionId>
          </base:Identifier>
        </gn:inspireId>
        <gn:leastDetailedViewingResolution nilReason="other:unpopulated" owns="false">
          <gmd:MD_Resolution>
            <gmd:equivalentScale></gmd:equivalentScale>
          </gmd:MD_Resolution>
        </gn:leastDetailedViewingResolution>
        <gn:localType gco:nilReason="other:unpopulated" uuidref="" xlink:type="simple" xlink:href="" xlink:role="none" xlink:arcrole="none" xlink:title="none" xlink:show="none" xlink:actuate="none">
          <gmd:LocalisedCharacterString></gmd:LocalisedCharacterString>
        </gn:localType>
        <gn:mostDetailedViewingResolution nilReason="other:unpopulated" owns="false">
          <gmd:MD_Resolution>
            <gmd:equivalentScale></gmd:equivalentScale>
          </gmd:MD_Resolution>
        </gn:mostDetailedViewingResolution>
        <gn:name>
          <gn:GeographicalName>
            <gn:language>NL</gn:language>
            <gn:nativeness>endonym</gn:nativeness>
            <gn:nameStatus  nilReason="other:unpopulated"></gn:nameStatus>
            <gn:sourceOfName>{fme:get-attribute('brontekst')}</gn:sourceOfName>
            <gn:pronunciation xmlns:xsi="http://www.w3.org/2001/XMLSchema-instance" nilReason="other:unpopulated" xsi:nil="true"/>
            <gn:spelling>
              <gn:SpellingOfName>
                <gn:text>{fme:get-attribute('naam')}</gn:text>
                 <gn:script>Latn</gn:script>
              </gn:SpellingOfName>
            </gn:spelling>
          </gn:GeographicalName>
        </gn:name>
        <gn:type codeSpace="urn:x-inspire:specification:gmlas:GeographicalNames:3.0/NamedPlaceTypeValue">{fme:get-attribute("type_decoded")}</gn:type>
      </gn:NamedPlace>
    VISIBLE_QUERY_VALIDATE = No
    OUTPUT_XML_HEADER = No
    -> AttributeCreator_3
CoordinateConcatenator_2
    COORD_ATTR = _coordinates
    COORD_DELIM = " "
    COORDINATES_TO_INCLUDE_DIS = X Y
    ELEMENT_DELIM = " "
    -> XMLTemplater_2
XMLTemplater_2
    RESULT_ATTRIBUTE = binary_object
    ROOT_QUERY_EXPR:
      <gn:NamedPlace xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2" gml:id="NL.KAD.BRT.GeographicalNames.{fme:get-attribute('identificatie')}">
        <gml:identifier codeSpace="http://inspire.jrc.ec.europa.eu/">
             urn:x-inspire:object:id:NL.KAD.BRT.GeographicalNames.{fme:get-attribute('identificatie')}
        </gml:identifier>
        <gn:beginLifespanVersion nilReason="">{fme:get-attribute("objectBeginTijd")}</gn:beginLifespanVersion>
        <gn:geometry>
          <gml:LineString srsName="urn:ogc:def:crs:EPSG::4258" srsDimension="2" gml:id="NL.KAD.BRT.GeographicalNames.{fme:get-attribute('identificatie')}_L">
            <gml:coordinates>{fme:get-attribute('_coordinates')}</gml:coordinates>
          </gml:LineString>
        </gn:geometry>
        <gn:inspireId>
          <base:Identifier>
            <base:localId>{fme:get-attribute('identificatie')}</base:localId>
            <base:namespace>NL.KAD.BRT.GeographicalNames</base:namespace>
            <base:versionId>{fme:get-attribute("versieBeginTijd")}</base:versionId>
          </base:Identifier>
        </gn:inspireId>
        <gn:leastDetailedViewingResolution nilReason="other:unpopulated" owns="false">
          <gmd:MD_Resolution>
            <gmd:equivalentScale></gmd:equivalentScale>
          </gmd:MD_Resolution>
        </gn:leastDetailedViewingResolution>
        <gn:localType gco:nilReason="other:unpopulated" uuidref="" xlink:type="simple" xlink:href="" xlink:role="none" xlink:arcrole="none" xlink:title="none" xlink:show="none" xlink:actuate="none">
          <gmd:LocalisedCharacterString></gmd:LocalisedCharacterString>
        </gn:localType>
        <gn:mostDetailedViewingResolution nilReason="other:unpopulated" owns="false">
          <gmd:MD_Resolution>
            <gmd:equivalentScale></gmd:equivalentScale>
          </gmd:MD_Resolution>
        </gn:mostDetailedViewingResolution>
        <gn:name>
          <gn:GeographicalName>
            <gn:language>NL</gn:language>
            <gn:nativeness>endonym</gn:nativeness>
            <gn:nameStatus  nilReason="other:unpopulated"></gn:nameStatus>
            <gn:sourceOfName>{fme:get-attribute('brontekst')}</gn:sourceOfName>
            <gn:pronunciation xmlns:xsi="http://www.w3.org/2001/XMLSchema-instance" nilReason="other:unpopulated" xsi:nil="true"/>
            <gn:spelling>
              <gn:SpellingOfName>
                <gn:text>{fme:get-attribute('naam')}</gn:text>
                 <gn:script>Latn</gn:script>
              </gn:SpellingOfName>
            </gn:spelling>
          </gn:GeographicalName>
        </gn:name>
        <gn:type codeSpace="urn:x-inspire:specification:gmlas:GeographicalNames:3.0/NamedPlaceTypeValue">{fme:get-attribute("type_decoded")}</gn:type>
      </gn:NamedPlace>
    VISIBLE_QUERY_VALIDATE = No
    OUTPUT_XML_HEADER = No
    -> AttributeCreator_3
DonutHoleExtractor
    OUTERSHELL -> CoordinateConcatenator
CoordinateConcatenator
    COORD_ATTR = exterior
    COORD_DELIM = " "
    COORDINATES_TO_INCLUDE_DIS = X Y
    ELEMENT_DELIM = " "
    -> XMLTemplater_3
XMLTemplater_3
    RESULT_ATTRIBUTE = binary_object
    ROOT_QUERY_EXPR:
      <gn:NamedPlace xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2" gml:id="NL.KAD.BRT.GeographicalNames.{fme:get-attribute('identificatie')}">
        <gml:identifier codeSpace="http://inspire.jrc.ec.europa.eu/">
             urn:x-inspire:object:id:NL.KAD.BRT.GeographicalNames.{fme:get-attribute('identificatie')}
        </gml:identifier>
        <gn:beginLifespanVersion nilReason="">{fme:get-attribute("objectBeginTijd")}</gn:beginLifespanVersion>
        <gn:geometry>
              <gml:MultiSurface gml:id="NL.KAD.BRT.GeographicalNames.{fme:get-attribute('identificatie')}_P" srsName="urn:ogc:def:crs:EPSG::4258" srsDimension="2" >
                <gml:surfaceMember>
                  <gml:Surface gml:id="Surface_NL.KAD.BRT.GeographicalNames.{fme:get-attribute('identificatie')}.1" srsName="urn:ogc:def:crs:EPSG::4258">
                    <gml:patches>
                      <gml:PolygonPatch interpolation="planar">
                        <gml:exterior>
                          <gml:LinearRing>
                            <gml:posList srsName="urn:ogc:def:crs:EPSG::4258" srsDimension="2">{fme:get-attribute("exterior")}</gml:posList>
                          </gml:LinearRing>
                        </gml:exterior>
                      </gml:PolygonPatch>
                    </gml:patches>
                  </gml:Surface>
                </gml:surfaceMember>
              </gml:MultiSurface>
        </gn:geometry>
        <gn:inspireId>
          <base:Identifier>
            <base:localId>{fme:get-attribute('identificatie')}</base:localId>
            <base:namespace>NL.KAD.BRT.GeographicalNames</base:namespace>
            <base:versionId>{fme:get-attribute("versieBeginTijd")}</base:versionId>
          </base:Identifier>
        </gn:inspireId>
        <gn:leastDetailedViewingResolution nilReason="other:unpopulated" owns="false">
          <gmd:MD_Resolution>
            <gmd:equivalentScale></gmd:equivalentScale>
          </gmd:MD_Resolution>
        </gn:leastDetailedViewingResolution>
        <gn:localType gco:nilReason="other:unpopulated" uuidref="" xlink:type="simple" xlink:href="" xlink:role="none" xlink:arcrole="none" xlink:title="none" xlink:show="none" xlink:actuate="none">
          <gmd:LocalisedCharacterString></gmd:LocalisedCharacterString>
        </gn:localType>
        <gn:mostDetailedViewingResolution nilReason="other:unpopulated" owns="false">
          <gmd:MD_Resolution>
            <gmd:equivalentScale></gmd:equivalentScale>
          </gmd:MD_Resolution>
        </gn:mostDetailedViewingResolution>
        <gn:name>
          <gn:GeographicalName>
            <gn:language>NL</gn:language>
            <gn:nativeness>endonym</gn:nativeness>
            <gn:nameStatus  nilReason="other:unpopulated"></gn:nameStatus>
            <gn:sourceOfName>{fme:get-attribute('brontekst')}</gn:sourceOfName>
            <gn:pronunciation xmlns:xsi="http://www.w3.org/2001/XMLSchema-instance" nilReason="other:unpopulated" xsi:nil="true"/>
            <gn:spelling>
              <gn:SpellingOfName>
                <gn:text>{fme:get-attribute('naam')}</gn:text>
                 <gn:script>Latn</gn:script>
              </gn:SpellingOfName>
            </gn:spelling>
          </gn:GeographicalName>
        </gn:name>
        <gn:type codeSpace="urn:x-inspire:specification:gmlas:GeographicalNames:3.0/NamedPlaceTypeValue">{fme:get-attribute("type_decoded")}</gn:type>
      </gn:NamedPlace>
    VISIBLE_QUERY_VALIDATE = No
    OUTPUT_XML_HEADER = No
    -> AttributeCreator_3
Note: ft=63 voor NamedPlace
AttributeCreator_3
    ATTR_LIST = ft_type,63,gml_id,NL.KAD.BRT.GeographicalNames.@Value(identificatie)
    -> BoundingBoxReplacer
BoundingBoxReplacer
    BOXTYPE = Bounding Box
    BOX -> CoordinateSwapper_2
Note: Omkeren volgorde lat en lon voor GML
CoordinateSwapper_2
    SWAP_TYPE = X <-> Y
    -> AttributeExpressionRemover
Note: Verwijderen alle originele / postgres attributen
AttributeExpressionRemover
    ATTR_EXP = postgis*
    -> inspire_gn.gml_objects (writer POSTGIS_1)
inspire_gn.gml_objects (writer POSTGIS_1)
    attributes: id serial,PRIKEY, gml_id text,none, ft_type int2, binary_object bytea
