FME workspace GN_typen2.fmw

Parameters:
- SourceDataset_GML = D:\Projects\PDOK\GeoNames\Scripts2pg\DATA\*.gml   # Source Geography Markup Language (GML) File(s)
- DestDataset_CSV = D:\Projects\PDOK\GeoNames\Scripts2pg\Type   # Destination Comma Separated Value (CSV) Directory

Readers:
- GML_1: GML from $(SourceDataset_GML)

Writers:
- CSV_1: CSV to $(DestDataset_CSV)

GeografischGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalInwoners xml_int32, geometrieVlak xml_geometry, labelPunt xml_geometry, naamNL{} xml_buffer, typeGeografischGebied xml_char(23), naamFries{} xml_buffer
    -> AttributeCopier
Terrein (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, fysiekVoorkomen{} xml_char(10), geometrieVlak xml_geometry, hoogteniveau xml_int32, naamFries{} xml_buffer, naamNL{} xml_buffer, typeLandgebruik xml_char(28), voorkomen{} xml_char(15)
    -> AttributeCopier
Gebouw (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieVlak xml_geometry, hoogte xml_real64, hoogteklasse xml_char(8), hoogteniveau xml_int32, naamNL{} xml_buffer, naamFries{} xml_buffer, status xml_char(34), typeGebouw{} xml_char(47)
    -> AttributeCopier
Hoogteverschil (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), lageZijde xml_geometry, hogeZijde xml_geometry
    -> AttributeCopier
Spoorbaandeel (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalSporen xml_int32, baanvaknaam{} xml_buffer, brugnaam{} xml_buffer, elektrificatie xml_char(21), fysiekVoorkomen{} xml_char(27), geometrieLijn xml_geometry, geometriePunt xml_geometry, hoogteniveau xml_int32, spoorbreedte xml_char(12), status xml_char(34), tunnelnaam{} xml_buffer, typeInfrastructuurSpoorbaandeel xml_char(10), typeSpoorbaan xml_char(7), vervoerfunctie xml_char(15)
    -> AttributeCopier
KadeOfWal (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometrieLijn xml_geometry
    -> AttributeCopier
Wegdeel (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalRijstroken xml_int32, afritnaam{} xml_buffer, afritnummer xml_buffer, aWegnummer{} xml_buffer, brugnaam{} xml_buffer, eWegnummer{} xml_buffer, fysiekVoorkomen{} xml_char(27), geometrieLijn xml_geometry, geometriePunt xml_geometry, geometrieVlak xml_geometry, gescheidenRijbaan xml_char(3), hartLijn xml_geometry, hartPunt xml_geometry, hoofdverkeersgebruik{} xml_char(27), hoogteniveau xml_int32, knooppuntnaam{} xml_buffer, nWegnummer{} xml_buffer, status xml_char(34),
      straatnaamFries{} xml_buffer, straatnaamNL{} xml_buffer, sWegnummer{} xml_buffer, tunnelnaam{} xml_buffer, typeInfrastructuurWegdeel xml_char(21), typeWeg{} xml_char(23), verhardingsbreedte xml_real64, verhardingsbreedteklasse xml_char(11), verhardingstype xml_char(12)
    -> AttributeCopier
IsoHoogte (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometrieLijn xml_geometry
    -> AttributeCopier
Inrichtingselement (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieLijn xml_geometry, geometriePunt xml_geometry, hoogte xml_real64, hoogteniveau xml_int32, naamNL{} xml_buffer, nummer{} xml_buffer, status xml_char(34), typeInrichtingselement xml_char(26), naamFries{} xml_buffer
    -> AttributeCopier
OverigRelief (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometriePunt xml_geometry, geometrieLijn xml_geometry
    -> AttributeCopier
FunctioneelGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieVlak xml_geometry, labelPunt xml_geometry, naamFries{} xml_buffer, naamNL{} xml_buffer, typeFunctioneelGebied xml_char(35)
    -> AttributeCopier
HoogteOfDieptePunt (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, functie xml_char(12), hoogte xml_real64, hoogteklasse xml_char(13), hoogteniveau xml_int32, naamFries{} xml_buffer, naamNL{} xml_buffer, status xml_char(34), typeRelief xml_char(21), geometriePunt xml_geometry
    -> AttributeCopier
Waterdeel (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, breedte xml_real64, breedteklasse xml_char(13), brugnaam xml_buffer, functie xml_char(16), fysiekVoorkomen{} xml_char(26), geometrieLijn xml_geometry, geometriePunt xml_geometry, geometrieVlak xml_geometry, hoofdafwatering xml_char(3), hoogteniveau xml_int32, naamFries{} xml_buffer, naamNL{} xml_buffer, scheepslaadvermogen xml_real64, sluisnaam xml_buffer, status xml_char(34), stroomrichting xml_char(33), typeInfrastructuurWaterdeel xml_char(18), typeWater xml_char(23),
      voorkomenWater xml_char(8)
    -> AttributeCopier
RegistratiefGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, geometrieVlak xml_geometry, labelPunt xml_geometry, naamFries{} xml_buffer, naamNL{} xml_buffer, nummer{} xml_int32, typeRegistratiefGebied xml_char(16)
    -> AttributeCopier
AttributeCopier
    ATTR_LIST = type,typeGeografischGebied,type,typeFunctioneelGebied,type,typeGebouw{0},type,typeSpoorbaan,type,typeWater,type,typeWeg{0},type,typeInrichtingselement,type,typeRelief
    -> GeometryRemover
GeometryRemover
    -> AttributeKeeper
AttributeKeeper
    KEEP_ATTRS = type,fme_basename
    -> DuplicateRemover
DuplicateRemover
    KEYATTR = type
    UNIQUE -> Sorter
Sorter
    SORT_PARM = type ALPHA ASCENDING
    SORTED -> GeografischGebied_type (writer CSV_1)
GeografischGebied_type (writer CSV_1)
    attributes: type char(100), INSPIRE char(23)
