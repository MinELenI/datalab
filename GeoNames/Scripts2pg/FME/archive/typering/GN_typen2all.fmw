FME workspace GN_typen2all.fmw

Parameters:
- SourceDataset_PATH = D:\Projects\PDOK\GeoNames\Scripts2pg\DATA   # Source Directory and File Pathnames Directory

Readers:
- PATH_1: PATH from $(SourceDataset_PATH)

PATH (reader PATH_1)
    attributes: path_unix buffer, path_windows buffer, path_rootname buffer, path_filename buffer, path_extension buffer, path_filesize buffer, path_ownername buffer, path_readonly buffer, path_modified_date date, path_created_date date, path_accessed_date date, path_directory_unix buffer, path_directory_windows buffer, path_type char(10)
    -> WorkspaceRunner
WorkspaceRunner
    WORKSPACE_FILE = $(FME_MF_DIR)GN_typen2.fmw
    BLOCKING = Yes
    WORKSPACE_PARAMETERS = SourceDataset_GML,@Value(path_windows),DestDataset_CSV,D:\Projects\PDOK\GeoNames\Scripts2pg\Type
