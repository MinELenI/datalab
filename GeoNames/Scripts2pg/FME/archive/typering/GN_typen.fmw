FME workspace GN_typen.fmw

Parameters:
- SourceDataset_GML = D:\Projects\PDOK\GeoNames\Scripts2pg\DATA\*.gml   # Source Geography Markup Language (GML) File(s)
- MAX_FEATURES =   # Max Features to Read
- DestDataset_CSV = D:\Projects\PDOK\GeoNames\Scripts2pg\LOG   # Destination Comma Separated Value (CSV) Directory

Readers:
- GML_1: GML from $(SourceDataset_GML)

Writers:
- CSV_1: CSV to $(DestDataset_CSV)

GeografischGebied (reader GML_1)
    attributes: identificatie xml_buffer, brontype xml_char(11), bronbeschrijving xml_buffer, bronactualiteit xml_char(10), bronnauwkeurigheid xml_real64, dimensie xml_char(2), objectBeginTijd xml_char(30), versieBeginTijd xml_char(30), objectEindTijd xml_char(30), versieEindTijd xml_char(30), visualisatieCode xml_int32, tdnCode xml_int32, aantalInwoners xml_int32, geometrieVlak xml_geometry, labelPunt xml_geometry, naamNL{} xml_buffer, typeGeografischGebied xml_char(23), naamFries{} xml_buffer
    -> GeometryRemover
GeometryRemover
    -> AttributeKeeper
AttributeKeeper
    KEEP_ATTRS = typeGeografischGebied
    -> DuplicateRemover
DuplicateRemover
    KEYATTR = typeGeografischGebied
    UNIQUE -> Sorter
Sorter
    SORT_PARM = typeGeografischGebied ALPHA ASCENDING
    SORTED -> GeografischGebied_type (writer CSV_1)
GeografischGebied_type (writer CSV_1)
    attributes: typeGeografischGebied char(23), INSPIRE char(23)
