FME workspace postgres2XML.fmw

Parameters:
- XML_DIR = ..\XML_OUT   # Fanout Directory
- LOG_FILE =   # Log File
- FT_TYPE = 61   # Type object
- MAX_FEATURES =   # Max Features to Read

Readers:
- POSTGRES_1: POSTGRES from pdok

Writers:
- TEXTLINE_1: TEXTLINE to D:\Projects\PDOK\GeoNames\Scripts2pg\XML_OUT\test_5.xml

inspire_gn.gml_objects (reader POSTGRES_1)
    attributes: id serial,PRIKEY, gml_id text,PRIKEY, ft_type int2, binary_object bytea, gml_bounded_by char(80),GIST
    -> StringReplacer
StringReplacer
    SRC_ATTRS = binary_object
    REGEXP = no
    CASE = no
    FIND_TEXT = xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2"
    -> AttributeCreator
AttributeCreator
    ATTR_LIST:
      text_line_data,<base:SpatialDataSet xmlns:gts="http://www.isotc211.org/2005/gts"
                                          xmlns:gn="urn:x-inspire:specification:gmlas:GeographicalNames:3.0 http://inspire.ec.europa.eu/schemas/gn/3.0/GeographicalNames.xsd"
                                          xmlns:xsi="http://www.w3.org/2001/XMLSchema-instance"
                                          xmlns:gco="http://www.isotc211.org/2005/gco"
                                          xmlns:gsr="http://www.isotc211.org/2005/gsr"
                                          xmlns:gss="http://www.isotc211.org/2005/gss"
                                          xmlns:gmd="http://www.isotc211.org/2005/gmd"
                                          xmlns:xlink="http://www.w3.org/1999/xlink"
                                          xmlns:base="urn:x-inspire:specification:gmlas:BaseTypes:3.2"
                                          xmlns:gml="http://www.opengis.net/gml/3.2"
                   gml:id="GeographicalNames.1">
        <base:identifier>
          <base:Identifier>
            <base:localId>0</base:localId>
            <base:namespace>NL.KAD.BRT</base:namespace>
            <base:versionId xsi:nil="true" nilReason="other:unpopulated"/>
          </base:Identifier>
        </base:identifier>
        <base:metadata xsi:nil="true"/>
       <base:member>
      @Value(binary_object)
       </base:member>
      </base:SpatialDataSet>
    -> text_line (writer TEXTLINE_1)
text_line (writer TEXTLINE_1)
    attributes: text_line_data buffer
BinaryDecoder [off]
    ATTR_ENCODING = utf-8
    ATTR_TO_DECODE = binary_object
    ENCODING_TYPE = HEX
    DEST_ATTR = _decoded
