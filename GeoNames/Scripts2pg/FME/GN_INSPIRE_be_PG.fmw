FME workspace GN_INSPIRE_be_PG.fmw

Parameters:
- LOG_FILE =   # Log File
- MAX_FEATURES =   # Max Features to Read

Readers:
- POSTGIS_1: POSTGIS from pdok

Writers:
- POSTGIS_2: POSTGIS to pdok

top10nl.functioneelgebied_point_imp (reader POSTGIS_1)
    attributes: identificatie text, brontype text, bronbeschrijving text, bronactualiteit text, bronnauwkeurigheid float8, dimensie text, objectbegintijd text, versiebegintijd text, objecteindtijd text, versieeindtijd text, visualisatiecode int8, tdncode int8, geometrievlak text, labelpunt text, naamfries text, naamnl text, typefunctioneelgebied text
    -> AttributeTrimmer_8
top10nl.gebouw_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, geometrievlak text, hoogte float8, hoogteklasse text, hoogteniveau int8, naamnl text, naamfries text, status text, typegebouw text
    -> AttributeTrimmer_8
top10nl.geografischgebied_point_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, aantalinwoners int8, labelpunt text, naamnl text, typegeografischgebied text, naamfries text
    -> AttributeTrimmer_8
top10nl.hoogteofdieptepunt_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, functie text, hoogte float8, hoogteklasse text, hoogteniveau int8, naamfries text, naamnl text, status text, typerelief text, geometriepunt text
    -> AttributeTrimmer_8
top10nl.hoogteverschil_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, functie text, hoogte float8, hoogteklasse text, hoogteniveau int8, naamfries text, naamnl text, status text, typerelief text, lagezijde text, hogezijde text
    -> AttributeTrimmer_8
top10nl.inrichtingselement_line_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, geometrielijn text, hoogte float8, hoogteniveau int8, naamnl text, nummer text, status text, typeinrichtingselement text, naamfries text
    -> AttributeTrimmer_8
top10nl.inrichtingselement_point_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, geometriepunt text, hoogte float8, hoogteniveau int8, naamnl text, nummer text, status text, typeinrichtingselement text, naamfries text
    -> AttributeTrimmer_8
top10nl.isohoogte_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, functie text, hoogte float8, hoogteklasse text, hoogteniveau int8, naamfries text, naamnl text, status text, typerelief text, geometrielijn text
    -> AttributeTrimmer_8
top10nl.kadeofwal_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, functie text, hoogte float8, hoogteklasse text, hoogteniveau int8, naamfries text, naamnl text, status text, typerelief text, geometrielijn text
    -> AttributeTrimmer_8
top10nl.registratiefgebied_poly_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, geometrievlak text, naamfries text, naamnl text, nummer int8, typeregistratiefgebied text
    -> AttributeTrimmer_8
top10nl.spoorbaandeel_line_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, aantalsporen int8, baanvaknaam text, brugnaam text, elektrificatie text, fysiekvoorkomen text, geometrielijn text, hoogteniveau int8, spoorbreedte text, status text, tunnelnaam text, typeinfrastructuurspoorbaandeel text, typespoorbaan text, vervoerfunctie text
    -> AttributeTrimmer_8
top10nl.spoorbaandeel_point_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, aantalsporen int8, baanvaknaam text, brugnaam text, elektrificatie text, fysiekvoorkomen text, geometriepunt text, hoogteniveau int8, spoorbreedte text, status text, tunnelnaam text, typeinfrastructuurspoorbaandeel text, typespoorbaan text, vervoerfunctie text
    -> AttributeTrimmer_8
top10nl.terrein_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, fysiekvoorkomen text, geometrievlak text, hoogteniveau int8, naamfries text, naamnl text, typelandgebruik text, voorkomen text
    -> AttributeTrimmer_8
top10nl.waterdeel_line_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, breedte float8, breedteklasse text, brugnaam text, functie text, fysiekvoorkomen text, geometrielijn text, hoofdafwatering text, hoogteniveau int8, naamfries text, naamnl text, scheepslaadvermogen float8, sluisnaam text, status text, stroomrichting text, typeinfrastructuurwaterdeel text, typewater text, voorkomenwater text
    -> AttributeTrimmer_8
top10nl.waterdeel_point_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, breedte float8, breedteklasse text, brugnaam text, functie text, fysiekvoorkomen text, geometriepunt text, hoofdafwatering text, hoogteniveau int8, naamfries text, naamnl text, scheepslaadvermogen float8, sluisnaam text, status text, stroomrichting text, typeinfrastructuurwaterdeel text, typewater text, voorkomenwater text
    -> AttributeTrimmer_8
top10nl.waterdeel_poly_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, breedte float8, breedteklasse text, brugnaam text, functie text, fysiekvoorkomen text, geometrievlak text, hoofdafwatering text, hoogteniveau int8, naamfries text, naamnl text, scheepslaadvermogen float8, sluisnaam text, status text, stroomrichting text, typeinfrastructuurwaterdeel text, typewater text, voorkomenwater text
    -> AttributeTrimmer_8
top10nl.wegdeel_line_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, aantalrijstroken int8, afritnaam text, afritnummer text, awegnummer text, brugnaam text, ewegnummer text, fysiekvoorkomen text, geometrielijn text, gescheidenrijbaan text, hartlijn text, hartpunt text, hoofdverkeersgebruik text, hoogteniveau int8, knooppuntnaam text, nwegnummer text, status text, straatnaamfries text,
      straatnaamnl text, swegnummer text, tunnelnaam text, typeinfrastructuurwegdeel text, typeweg text, verhardingsbreedte float8, verhardingsbreedteklasse text, verhardingstype text
    -> AttributeTrimmer_8
top10nl.wegdeel_point_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, aantalrijstroken int8, afritnaam text, afritnummer text, awegnummer text, brugnaam text, ewegnummer text, fysiekvoorkomen text, geometriepunt text, gescheidenrijbaan text, hartlijn text, hartpunt text, hoofdverkeersgebruik text, hoogteniveau int8, knooppuntnaam text, nwegnummer text, status text, straatnaamfries text,
      straatnaamnl text, swegnummer text, tunnelnaam text, typeinfrastructuurwegdeel text, typeweg text, verhardingsbreedte float8, verhardingsbreedteklasse text, verhardingstype text
    -> AttributeTrimmer_8
top10nl.wegdeel_poly_imp (reader POSTGIS_1)
    attributes: gid serial,PRIKEY, identificatie text, brontype text, bronbeschrijving text, bronactualiteit text, bronnauwkeurigheid float8, dimensie text, objectbegintijd text, versiebegintijd text, objecteindtijd text, versieeindtijd text, visualisatiecode int8, tdncode int8, aantalrijstroken int8, afritnaam text, afritnummer text, awegnummer text, brugnaam text, ewegnummer text, fysiekvoorkomen text, geometrievlak text, gescheidenrijbaan text, hartlijn text, hartpunt text, hoofdverkeersgebruik text, hoogteniveau int8, knooppuntnaam text, nwegnummer text, status text, straatnaamfries text,
      straatnaamnl text, swegnummer text, tunnelnaam text, typeinfrastructuurwegdeel text, typeweg text, verhardingsbreedte float8, verhardingsbreedteklasse text, verhardingstype text
    -> AttributeTrimmer_8
AttributeTrimmer_8
    SRC_ATTRS = naamfries,naamnl,baanvaknaam,brugnaam,tunnelnaam,sluisnaam,afritnaam,knooppuntnaam,straatnaamfries,straatnaamnl
    TRIM_TO_NONE = Yes
    TRIM_TYPE = Both
    -> Tester_naamnl
    -> Tester_naamfries
    -> Tester_baanvaknaam
    -> Tester_brugnaam
    -> Tester_tunnelnaam
    -> Tester_afritnaam
    -> Tester_knooppuntnaam
    -> Tester_straatnaamnl
    -> Tester_straatnaamfries
Tester_straatnaamfries
    TEST_MODE = Automatic
    TEST_DESCRIPTION = ""
    BOOL_OP = AND
    TEST_CLAUSE:
      TEST straatnaamfries ATTRIBUTE_EXISTS <Unused>
      TEST straatnaamfries NOT_ATTRIBUTE_IS_EMPTY <Unused>
      TEST straatnaamfries NOT_ATTRIBUTE_IS_NULL <Unused>
    PASSED -> AttributeCopier_8
AttributeCopier_8
    ATTR_LIST = naam,straatnaamfries
    -> AttributeCreator_4
Tester_naamfries
    TEST_MODE = Automatic
    TEST_DESCRIPTION = ""
    BOOL_OP = AND
    TEST_CLAUSE:
      TEST naamfries ATTRIBUTE_EXISTS <Unused>
      TEST naamfries NOT_ATTRIBUTE_IS_EMPTY <Unused>
      TEST naamfries NOT_ATTRIBUTE_IS_NULL <Unused>
    PASSED -> AttributeCopier_4
AttributeCopier_4
    ATTR_LIST = naam,naamfries
    -> AttributeCreator_4
AttributeCreator_4
    ATTR_LIST = taal,FR
    -> AttributeCopier_12
Tester_naamnl
    TEST_MODE = Automatic
    TEST_DESCRIPTION = ""
    BOOL_OP = AND
    TEST_CLAUSE:
      TEST naamnl ATTRIBUTE_EXISTS <Unused>
      TEST naamnl NOT_ATTRIBUTE_IS_EMPTY <Unused>
      TEST naamnl NOT_ATTRIBUTE_IS_NULL <Unused>
    PASSED -> AttributeCopier_3
AttributeCopier_3
    ATTR_LIST = naam,naamnl
    -> AttributeCreator_2
Tester_baanvaknaam
    TEST_MODE = Automatic
    TEST_DESCRIPTION = ""
    BOOL_OP = AND
    TEST_CLAUSE:
      TEST baanvaknaam ATTRIBUTE_EXISTS <Unused>
      TEST baanvaknaam NOT_ATTRIBUTE_IS_EMPTY <Unused>
      TEST baanvaknaam NOT_ATTRIBUTE_IS_NULL <Unused>
    PASSED -> AttributeCopier_2
AttributeCopier_2
    ATTR_LIST = naam,baanvaknaam
    -> AttributeCreator_2
Tester_brugnaam
    TEST_MODE = Automatic
    TEST_DESCRIPTION = ""
    BOOL_OP = AND
    TEST_CLAUSE:
      TEST brugnaam ATTRIBUTE_EXISTS <Unused>
      TEST brugnaam NOT_ATTRIBUTE_IS_EMPTY <Unused>
      TEST brugnaam NOT_ATTRIBUTE_IS_NULL <Unused>
    PASSED -> AttributeCopier_5
AttributeCopier_5
    ATTR_LIST = naam,brugnaam
    -> AttributeCreator_2
Tester_tunnelnaam
    TEST_MODE = Automatic
    TEST_DESCRIPTION = ""
    BOOL_OP = AND
    TEST_CLAUSE:
      TEST tunnelnaam ATTRIBUTE_EXISTS <Unused>
      TEST tunnelnaam NOT_ATTRIBUTE_IS_EMPTY <Unused>
      TEST tunnelnaam NOT_ATTRIBUTE_IS_NULL <Unused>
    PASSED -> AttributeCopier_6
AttributeCopier_6
    ATTR_LIST = naam,tunnelnaam
    -> AttributeCreator_2
Tester_afritnaam
    TEST_MODE = Automatic
    TEST_DESCRIPTION = ""
    BOOL_OP = AND
    TEST_CLAUSE:
      TEST afritnaam ATTRIBUTE_EXISTS <Unused>
      TEST afritnaam NOT_ATTRIBUTE_IS_EMPTY <Unused>
      TEST afritnaam NOT_ATTRIBUTE_IS_NULL <Unused>
    PASSED -> AttributeCopier_7
AttributeCopier_7
    ATTR_LIST = naam,afritnaam
    -> AttributeCreator_2
Tester_knooppuntnaam
    TEST_MODE = Automatic
    TEST_DESCRIPTION = ""
    BOOL_OP = AND
    TEST_CLAUSE:
      TEST knooppuntnaam ATTRIBUTE_EXISTS <Unused>
      TEST knooppuntnaam NOT_ATTRIBUTE_IS_EMPTY <Unused>
      TEST knooppuntnaam NOT_ATTRIBUTE_IS_NULL <Unused>
    PASSED -> AttributeCopier_9
AttributeCopier_9
    ATTR_LIST = naam,knooppuntnaam
    -> AttributeCreator_2
Tester_straatnaamnl
    TEST_MODE = Automatic
    TEST_DESCRIPTION = ""
    BOOL_OP = AND
    TEST_CLAUSE:
      TEST straatnaamnl ATTRIBUTE_EXISTS <Unused>
      TEST straatnaamnl NOT_ATTRIBUTE_IS_EMPTY <Unused>
      TEST straatnaamnl NOT_ATTRIBUTE_IS_NULL <Unused>
    PASSED -> AttributeCopier_10
AttributeCopier_10
    ATTR_LIST = naam,straatnaamnl
    -> AttributeCreator_2
AttributeCreator_2
    ATTR_LIST = taal,NL
    -> AttributeCopier_12
AttributeCopier_12
    ATTR_LIST = type,typefunctioneelgebied,type,typegebouw,type,typespoorbaan,type,typewater,type,typeweg,type,typeinrichtingselement,type,typegeografischgebied,type,typeregistratiefgebied,type,typerelief
    -> StringReplacer
StringReplacer
    SRC_ATTRS = identificatie
    REGEXP = no
    CASE = no
    FIND_TEXT = NL.TOP10NL.
    -> AttributeKeeper
AttributeKeeper
    KEEP_ATTRS = identificatie,objectbegintijd,versiebegintijd,objecteindtijd,versieeindtijd,type,naam,taal
    -> DateFormatter
DateFormatter
    DATE_ATTR = objectbegintijd,versiebegintijd,objecteindtijd,versieeindtijd
    FMT = %Y-%m-%dT%H:%M:%S
    -> CsmapReprojector
Note: Reprojectie naar EPSG:4258
CsmapReprojector
    DEST = EPSG:4258
    RASTER_CELL_SIZE = Preserve Cells
    TRANSFORMATION = Amersfoort-RD-2008_to_ETRS89/01_USER
    SOURCE = Netherlands-RDNew-2008
    INTERPOLATION_TYPE_NAME = Nearest Neighbor
    VERTICAL_HANDLING = Ignore heights and leave them unchanged
    REPROJECTED -> AttributeValueMapper
AttributeValueMapper
    DIRECTION = Forward (Source To Destination)
    VAL_ATTR = type_decoded
    DEFAULT_VALUE = other
    LUT = GPS kernnetpunt,other,RD punt,other,bank, ondiepte, plaat,hydrography,bron, wel,hydrography,camping, kampeerterrein,landcover,dam, koedam,hydrography,dierentuin, safaripark,landcover,gedenkteken, monument,other,geul, vaargeul,hydrography,greppel, droge sloot,hydrography,heg, haag,landcover,heuvel, berg,landform,kaap, hoek,hydrography,kade, wal,landform,kas, warenhuis,building,kazerne, legerplaats,landcover,kerncentrale, kernreactor,building,kilometerpaal spoorweg,other,kilometerpaal water,other,kliniek, inrichting, sanatorium,building,klooster, abdij,building,kogelvanger schietbaan,other,licht, lichtopstand,other,lokale weg,transportNetwork,markant object,other,meer, plas, ven, vijver,hydrography,militair gebouw,building,militair oefengebied, schietterrein,landcover,natuurgebied, natuurreservaat,protectedSite,parkeerdak, parkeerdek, parkeergarage,building,plaats, bewoond oord,populatedPlace,psychiatrisch ziekenhuis, psychiatrisch centrum,building,radiotoren, televisietoren,building,regionale weg,transportNetwork,religieus gebouw,building,rolbaan, platform,transportNetwork,sportterrein, sportcomplex,landcover,startbaan, landingsbaan,transportNetwork,steile rand, aardrand,landform,streek, veld,landform,talud, hoogteverschil,landform,vliegveld, luchthaven,landcover,windmolen: korenmolen,building,windmolen: watermolen,building,zeegat, zeearm,hydrography,zichtbaar wrak,other,zwembad complex,building,aanlegsteiger,landcover,afrit,transportNetwork,arboretum,landcover,autosnelweg,transportNetwork,baak,other,baanvak,transportNetwork,bedrijventerrein,landcover,begraafplaats,landcover,bezoekerscentrum,building,bomenrij,landcover,boom,landcover,bosgebied,landcover,boswachterij,landcover,brandtoren,building,brug,transportNetwork,bungalowpark,populatedPlace,bunker,building,buurtschap,populatedPlace,caravanpark,populatedPlace,circuit,landcover,crematorium,building,crossbaan,landcover,deelraadsecretarie,building,dieptelijn,other,dieptepunt,other,dok,hydrography,droogvallend,hydrography,duingebied,landform,dukdalf,hydrography,eendenkooi,hydrography,eiland,landform,elektriciteitscentrale,building,emplacement,landcover,erebegraafplaats,landcover,fabriek,building,fort,building,gaswinning,landcover,gebouwencomplex,building,geluidswering,other,gemaal,building,gemeentehuis,building,gevangenis,building,golfmeetpaal,other,golfterrein,landcover,grafheuvel,landform,grenspunt,other,grindwinning,landcover,groeve,landcover,haven,hydrography,heemtuin,landcover,heidegebied,landcover,hekwerk,landcover,helikopterlandingsplatform,other,helikopterlandingsterrein,landcover,hoofdweg,transportNetwork,hoogspanningsleiding,other,hoogspanningsmast,other,hoogtelijn,other,hoogtepunt,other,hotel,building,huizenblok,populatedPlace,huizengroep,populatedPlace,hulpsecretarie,building,hunebed,landcover,ijsbaan,landcover,infiltratiegebied,hydrography,jachthaven,hydrography,kaap,hydrography,kabelbaan,transportNetwork,kabelbaanmast,other,kapel,building,kartingbaan,landcover,kasteel,building,kerk,building,kilometerpaal,other,kilometerraaibord,other,kilometerraaipaal,other,klokkentoren,building,knooppunt,transportNetwork,koeltoren,building,koepel,building,kraan,building,kruis,other,kunstijsbaan,building,laadperron,landcover,laagwaterlijn,other,landgoed,landcover,lichttoren,building,luchtwachttoren,building,manege,building,metro,transportNetwork,metrostation,building,mijn,landcover,mosselbank,hydrography,motel,building,museum,building,muur,building,oliepompinstallatie,other,oliewinning,landcover,onbekend,other,openluchtmuseum,landcover,openluchttheater,other,overig,other,paal,other,paalwerk,other,park,landcover,peil,other,peilmeetstation,building,peilschaal,other,pijler,building,pinetum,landcover,plantsoen,landcover,polder,landform,politiebureau,building,pompstation,building,postkantoor,building,productie-installatie,building,radarpost,building,radartoren,building,radiobaken,other,radiotelescoop,building,recreatiecentrum,building,recreatiegebied,landcover,reddingboothuisje,building,remise,building,renbaan,landcover,ruïne,building,schaapskooi,building,schietbaan,other,school,building,schoorsteen,building,seinmast,other,skibaan,other,slipschool,other,sluisdeur,hydrography,sluizencomplex,hydrography,sporthal,building,stadion,building,stadskantoor,building,station,building,stormvloedkering,building,stortplaats,landcover,straat,transportNetwork,strandpaal,other,stuw,hydrography,tank,building,tankstation,building,telecommunicatietoren,building,tennispark,landcover,terp,landform,tol,transportNetwork,toren,building,tram,transportNetwork,transformatorstation,building,trein,transportNetwork,treinstation,building,tuincentrum,building,tunnel,transportNetwork,uitzichttoren,building,universiteit,building,veiling,building,verkeersgeleider,other,verkeerstoren,building,verzorgingsplaats,other,viskwekerij,hydrography,vlampijp,building,vliedberg,landform,volkstuinen,landcover,vuurtoren,building,waterloop,hydrography,waterradmolen,building,watertoren,building,wegafsluiting,transportNetwork,wegenwachtstation,building,wegrestaurant,building,wegwijzer,transportNetwork,werf,building,wildwissel,other,windmolen,building,windmolentje,other,windturbine,building,windturbinepark,landcover,woonwagencentrum,populatedPlace,woonwijk,populatedPlace,zandwinning,landcover,zee,hydrography,zenderpark,landcover,zendmast,building,zendtoren,building,ziekenhuis,building,zoutwinning,landcover,zuiveringsinstallatie,building,zweefvliegveldterrein,landcover,zwembad,building
    SRC = type
    -> AttributeCreator
AttributeCreator
    ATTR_LIST = brontekst,De Basisregistratie Topografie (BRT) bestaat uit digitale topografische bestanden op verschillende schaalniveaus. Het uit de BRT afgeleide TOP10NL is een digitaal objectgericht topografisch bestand wat ten grondslag ligt aan de topografische kaartseries 1:10.000 en 1:25.000 en wat veelvuldig in diverse GIS- en CAD-systemen wordt gebruikt voor ondergrond, analyse-, en beheers- en planningsactiviteiten.
    -> GeometryExtractor
GeometryExtractor
    ATTR = _geometry
    OMIT_NAMESPACES_DISPLAY = Yes
    KIND_LONG = GML v3.2.1
    -> Matcher
Matcher
    MATCHATTRS = identificatie
    BLANK_AND_MISSING_DIFFER_DISP = As Missing Attribute
    MATCH = NONE
    MATCH_STRATEGY = Match Selected Attributes
    LENIENT_MATCH = No
    CNT_ATTR = _match_id
    MATCHED -> AttributeKeeper_2
    SINGLE_MATCHED -> XMLTemplater_3 [input 1]
    NOT_MATCHED -> XMLTemplater_2
AttributeKeeper_2
    KEEP_ATTRS = identificatie,naam,taal,brontekst
    -> GeometryRemover
GeometryRemover
    -> XMLTemplater_3 [input 2]
XMLTemplater_3
    GROUP_BY = identificatie
    RESULT_ATTRIBUTE = binary_object
    NAME_QUERY_EXPR:
        <gn:name>
          <gn:GeographicalName>
            <gn:language>{fme:get-attribute("taal")}</gn:language>
            <gn:nativeness>endonym</gn:nativeness>
            <gn:nameStatus  nilReason="other:unpopulated"></gn:nameStatus>
            <gn:sourceOfName>{fme:get-attribute('brontekst')}</gn:sourceOfName>
            <gn:pronunciation xmlns:xsi="http://www.w3.org/2001/XMLSchema-instance" nilReason="other:unpopulated" xsi:nil="true"/>
            <gn:spelling>
              <gn:SpellingOfName>
                <gn:text>{fme:get-attribute('naam')}</gn:text>
                 <gn:script>Latn</gn:script>
              </gn:SpellingOfName>
            </gn:spelling>
          </gn:GeographicalName>
        </gn:name>
    ROOT_QUERY_EXPR:
      <gn:NamedPlace xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2" gml:id="NL.KAD.BRT.GeographicalNames.{fme:get-attribute('identificatie')}">
        <gml:identifier codeSpace="http://inspire.jrc.ec.europa.eu/">
             urn:x-inspire:object:id:NL.KAD.BRT.GeographicalNames.{fme:get-attribute('identificatie')}
        </gml:identifier>
        <gn:beginLifespanVersion nilReason="">{fme:get-attribute("objectbegintijd")}</gn:beginLifespanVersion>
        <gn:geometry>{fme:get-attribute("_geometry")}</gn:geometry>
        <gn:inspireId>
          <base:Identifier>
            <base:localId>{fme:get-attribute('identificatie')}</base:localId>
            <base:namespace>NL.KAD.BRT.GeographicalNames</base:namespace>
            <base:versionId>{fme:get-attribute("versiebegintijd")}</base:versionId>
          </base:Identifier>
        </gn:inspireId>
        <gn:leastDetailedViewingResolution nilReason="other:unpopulated" owns="false">
          <gmd:MD_Resolution>
            <gmd:equivalentScale></gmd:equivalentScale>
          </gmd:MD_Resolution>
        </gn:leastDetailedViewingResolution>
        <gn:localType gco:nilReason="other:unpopulated" uuidref="" xlink:type="simple" xlink:href="" xlink:role="none" xlink:arcrole="none" xlink:title="none" xlink:show="none" xlink:actuate="none">
          <gmd:LocalisedCharacterString></gmd:LocalisedCharacterString>
        </gn:localType>
        <gn:mostDetailedViewingResolution nilReason="other:unpopulated" owns="false">
          <gmd:MD_Resolution>
            <gmd:equivalentScale></gmd:equivalentScale>
          </gmd:MD_Resolution>
        </gn:mostDetailedViewingResolution>
         {fme:process-features("NAME", "identificatie", fme:get-attribute("identificatie"))}
        <gn:type codeSpace="urn:x-inspire:specification:gmlas:GeographicalNames:3.0/NamedPlaceTypeValue">{fme:get-attribute("type_decoded")}</gn:type>
      </gn:NamedPlace>
    VISIBLE_QUERY_VALIDATE = No
    OUTPUT_XML_HEADER = No
    -> AttributeCreator_3
XMLTemplater_2
    RESULT_ATTRIBUTE = binary_object
    ROOT_QUERY_EXPR:
      <gn:NamedPlace xmlns:gts="http://www.isotc211.org/2005/gts" xmlns:gn="urn:x-inspire:specification:gmlas:GeographicalNames:3.0" xmlns:gco="http://www.isotc211.org/2005/gco" xmlns:gsr="http://www.isotc211.org/2005/gsr" xmlns:gss="http://www.isotc211.org/2005/gss" xmlns:gmd="http://www.isotc211.org/2005/gmd" xmlns:xlink="http://www.w3.org/1999/xlink" xmlns:base="urn:x-inspire:specification:gmlas:BaseTypes:3.2" xmlns:gml="http://www.opengis.net/gml/3.2" gml:id="NL.KAD.BRT.GeographicalNames.{fme:get-attribute('identificatie')}">
        <gml:identifier codeSpace="http://inspire.jrc.ec.europa.eu/">
             urn:x-inspire:object:id:NL.KAD.BRT.GeographicalNames.{fme:get-attribute('identificatie')}
        </gml:identifier>
        <gn:beginLifespanVersion nilReason="">{fme:get-attribute("objectbegintijd")}</gn:beginLifespanVersion>
        <gn:geometry>{fme:get-attribute("_geometry")}</gn:geometry>
        <gn:inspireId>
          <base:Identifier>
            <base:localId>{fme:get-attribute('identificatie')}</base:localId>
            <base:namespace>NL.KAD.BRT.GeographicalNames</base:namespace>
            <base:versionId>{fme:get-attribute("versiebegintijd")}</base:versionId>
          </base:Identifier>
        </gn:inspireId>
        <gn:leastDetailedViewingResolution nilReason="other:unpopulated" owns="false">
          <gmd:MD_Resolution>
            <gmd:equivalentScale></gmd:equivalentScale>
          </gmd:MD_Resolution>
        </gn:leastDetailedViewingResolution>
        <gn:localType gco:nilReason="other:unpopulated" uuidref="" xlink:type="simple" xlink:href="" xlink:role="none" xlink:arcrole="none" xlink:title="none" xlink:show="none" xlink:actuate="none">
          <gmd:LocalisedCharacterString></gmd:LocalisedCharacterString>
        </gn:localType>
        <gn:mostDetailedViewingResolution nilReason="other:unpopulated" owns="false">
          <gmd:MD_Resolution>
            <gmd:equivalentScale></gmd:equivalentScale>
          </gmd:MD_Resolution>
        </gn:mostDetailedViewingResolution>
        <gn:name>
          <gn:GeographicalName>
            <gn:language>{fme:get-attribute("taal")}</gn:language>
            <gn:nativeness>endonym</gn:nativeness>
            <gn:nameStatus  nilReason="other:unpopulated"></gn:nameStatus>
            <gn:sourceOfName>{fme:get-attribute('brontekst')}</gn:sourceOfName>
            <gn:pronunciation xmlns:xsi="http://www.w3.org/2001/XMLSchema-instance" nilReason="other:unpopulated" xsi:nil="true"/>
            <gn:spelling>
              <gn:SpellingOfName>
                <gn:text>{fme:get-attribute('naam')}</gn:text>
                 <gn:script>Latn</gn:script>
              </gn:SpellingOfName>
            </gn:spelling>
          </gn:GeographicalName>
        </gn:name>
        <gn:type codeSpace="urn:x-inspire:specification:gmlas:GeographicalNames:3.0/NamedPlaceTypeValue">{fme:get-attribute("type_decoded")}</gn:type>
      </gn:NamedPlace>
    VISIBLE_QUERY_VALIDATE = No
    OUTPUT_XML_HEADER = No
    -> AttributeCreator_3
Note: ft=63 voor NamedPlace
AttributeCreator_3
    ATTR_LIST = ft_type,63,gml_id,NL.KAD.BRT.GeographicalNames.@Value(identificatie)
    -> BoundingBoxReplacer
BoundingBoxReplacer
    BOXTYPE = Bounding Box
    BOX -> AttributeExpressionRemover
Note: Verwijderen alle originele / postgres attributen
AttributeExpressionRemover
    ATTR_EXP = postgis*
    -> BinaryEncoder
BinaryEncoder
    ENCODING_TYPE = HEX
    ATTR_TO_ENCODE = binary_object
    DEST_ATTR = binary_object
    -> inspire_gn.gml_objects (writer POSTGIS_2)
inspire_gn.gml_objects (writer POSTGIS_2)
    attributes: id serial,PRIKEY, gml_id text,none, ft_type int2, binary_object bytea
