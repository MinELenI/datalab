FME workspace xsd2xml_GN.fmw

Parameters:
- DestDataset_TEXTLINE = D:\Projects\PDOK\GeoNames\Scripts2pg\XML_template\GN.xml   # Destination Text File File

Writers:
- TEXTLINE_1: TEXTLINE to $(DestDataset_TEXTLINE)

Creator
    NUM = 1
    GEOMTYPE = Geometry Object
    CREATED -> GN_XMLSampleGenerator
    CREATED -> GN_XMLSampleGenerator_2
GN_XMLSampleGenerator: XMLSampleGenerator
    PATH_TO_ELEMENT = gn:GeographicalName
    RESULT_ATTRIBUTE = _result
    GENERATE_OPTIONAL_ATTRIBUTES = Yes
    GENERATE_COMMENTS = No
    CHOICE_OPTIONS = Generate no options
    GENERATE_HEADER = Yes
    SCHEMA_LOCATION = D:\Projects\PDOK\XSD\GeographicalNames.xsd
    GENERATE_OPTIONAL_ELEMENTS = Yes
    SUBSTITUTION_GROUP_OPTIONS = Generate all members
    -> AttributeCopier
GN_XMLSampleGenerator_2: XMLSampleGenerator
    PATH_TO_ELEMENT = gn:NamedPlace
    RESULT_ATTRIBUTE = _result
    GENERATE_OPTIONAL_ATTRIBUTES = Yes
    GENERATE_COMMENTS = No
    CHOICE_OPTIONS = Generate no options
    GENERATE_HEADER = Yes
    SCHEMA_LOCATION = D:\Projects\PDOK\XSD\GeographicalNames.xsd
    GENERATE_OPTIONAL_ELEMENTS = Yes
    SUBSTITUTION_GROUP_OPTIONS = Generate all members
    -> AttributeCopier
AttributeCopier
    ATTR_LIST = text_line_data,_result
    -> text_line (writer TEXTLINE_1)
text_line (writer TEXTLINE_1)
    attributes: text_line_data buffer
